package 'System' {
  requirement def 'CA-DM-CON-ICD-0007' { doc /*  */ }
  requirement def 'CA-DM-CON-ICD-0008' { doc /*  */ }
  requirement def 'CA-DM-CON-ICD-0013' { doc /*  */ }
  requirement def 'CA-DM-CON-ICD-0014' { doc /*  */ }
  requirement def 'CA-DM-CON-ICD-0015' { doc /*  */ }
  requirement def 'CA-DM-CON-ICD-0016' { doc /*  */ }
  requirement def 'CA-DM-CON-ICD-0017' { doc /*  */ }
  requirement def 'DMSR-2491' { doc /*  */ }
  requirement def 'DMSR-6406' { doc /*  */ }
  requirement def 'DMSR-1478' { doc /*  */ }
  requirement def 'DMSR-3563' { doc /*  */ }
  requirement def 'DMSR-7763' { doc /*  */ }
  requirement def 'DMSR-5876' { doc /*  */ }
  requirement def 'DMSR-6585' { doc /*  */ }
  requirement def 'DMSR-8525' { doc /*  */ }
  requirement def 'DMSR-7692' { doc /*  */ }
  requirement def 'DMSR-9449' { doc /*  */ }
  requirement def 'DMSR-1786' { doc /*  */ }
  requirement def 'DMSR-2005' { doc /*  */ }
  requirement def 'DMSR-8325' { doc /*  */ }
  requirement def 'DMSR-3617' { doc /*  */ }
  requirement def 'DMSR-6475' { doc /*  */ }
  requirement def 'DMSR-8494' { doc /*  */ }
  requirement def 'DMSR-3337' { doc /*  */ }
  requirement def 'DMSR-9599' { doc /*  */ }
  requirement def 'DMSR-7847' { doc /*  */ }
  requirement def 'DMSR-6570' { doc /*  */ }
  requirement def 'DMSR-1963' { doc /*  */ }
  requirement def 'DMSR-3004' { doc /*  */ }
  requirement def 'DMSR-3997' { doc /*  */ }
  requirement def 'DMSR-5135' { doc /*  */ }
  requirement def 'DMSR-5970' { doc /*  */ }
  requirement def 'DMSR-6300' { doc /*  */ }
  requirement def 'DMSR-1236' { doc /*  */ }
  requirement def 'DMSR-5909' { doc /*  */ }
  requirement def 'DMSR-1570' { doc /*  */ }
  requirement def 'DMSR-7309' { doc /*  */ }
  requirement def 'DMSR-6873' { doc /*  */ }
  requirement def 'DMSR-4221' { doc /*  */ }
  requirement def 'DMSR-9952' { doc /*  */ }
  requirement def 'DMSR-9915' { doc /*  */ }
  requirement def 'DMSR-8151' { doc /*  */ }
  requirement def 'DMSR-3053' { doc /*  */ }
  requirement def 'DMSR-8254' { doc /*  */ }
  requirement def 'DMSR-9289' { doc /*  */ }
  requirement def 'DMSR-9487' { doc /*  */ }
  requirement def 'DMSR-9351' { doc /*  */ }
  requirement def 'DMSR-9504' { doc /*  */ }
  requirement def 'DMSR-1578' { doc /*  */ }
  requirement def 'DMSR-3565' { doc /*  */ }
  requirement def 'DMSR-9563' { doc /*  */ }
  requirement def 'DMSR-2324' { doc /*  */ }
  requirement def 'DMSR-8893' { doc /*  */ }
  requirement def 'DMSR-9422' { doc /*  */ }
  requirement def 'DMSR-3721' { doc /*  */ }
  requirement def 'DMSR-2127' { doc /*  */ }
  requirement def 'DMSR-5792' { doc /* The LSST Project shall provide data access services for the current Level 1 data, the most recent nDRMin Data Releases, and multiple older Data Releases. */ }
  requirement def 'DMSR-5457' { doc /*  */ }
  requirement def 'DMSR-6515' { doc /*  */ }
  requirement def 'DMSR-6206' { doc /*  */ }
  requirement def 'DMSR-6023' { doc /*  */ }
  requirement def 'DMSR-1591' { doc /*  */ }
  requirement def 'DMSR-3753' { doc /*  */ }
  requirement def 'DMSR-3770' { doc /*  */ }
  requirement def 'DMSR-6987' { doc /*  */ }
  requirement def 'DMSR-9580' { doc /*  */ }
  requirement def 'DMSR-2551' { doc /*  */ }
  requirement def 'DMSR-8635' { doc /*  */ }
  requirement def 'DMSR-8958b' { doc /*  */ }
  requirement def 'DMSR-9850' { doc /*  */ }
  requirement def 'DMSR-1436' { doc /*  */ }
  requirement def 'DMSR-1933' { doc /*  */ }
  requirement def 'DMSR-3612' { doc /*  */ }
  requirement def 'DMSR-9308' { doc /*  */ }
  requirement def 'DMSR-2058' { doc /*  */ }
  requirement def 'DMSR-5729' { doc /*  */ }
  requirement def 'OCS-DM-COM-ICD-0013' { doc /*  */ }
  requirement def 'OCS-DM-COM-ICD-0014' { doc /*  */ }
  requirement def 'OCS-DM-COM-ICD-0015' { doc /*  */ }
  requirement def 'OCS-DM-COM-ICD-0017' { doc /*  */ }
  requirement def 'OCS-DM-COM-ICD-0018' { doc /*  */ }
  requirement def 'OCS-DM-COM-ICD-0019' { doc /*  */ }
  requirement def 'OCS-DM-COM-ICD-0020' { doc /*  */ }
  requirement def 'OCS-DM-COM-ICD-0021' { doc /*  */ }
  requirement def 'OCS-DM-COM-ICD-0022' { doc /*  */ }
  requirement def 'OCS-DM-COM-ICD-0025' { doc /*  */ }
  requirement def 'OCS-DM-COM-ICD-0026' { doc /*  */ }
  requirement def 'OCS-DM-COM-ICD-0027' { doc /*  */ }
  requirement def 'OCS-DM-COM-ICD-0028' { doc /*  */ }
  requirement def 'OCS-DM-COM-ICD-0029' { doc /*  */ }
  requirement def 'OCS-DM-COM-ICD-0030' { doc /*  */ }
  requirement def 'OCS-DM-COM-ICD-0032' { doc /*  */ }
  requirement def 'OCS-DM-COM-ICD-0033' { doc /*  */ }
  requirement def 'OCS-DM-COM-ICD-0034' { doc /*  */ }
  requirement def 'OCS-DM-COM-ICD-0035' { doc /*  */ }
  requirement def 'OCS-DM-COM-ICD-0036' { doc /*  */ }
  requirement def 'OCS-DM-COM-ICD-0037' { doc /*  */ }
  requirement def 'OCS-DM-COM-ICD-0038' { doc /*  */ }
  requirement def 'OCS-DM-COM-ICD-0039' { doc /*  */ }
  requirement def 'OCS-DM-COM-ICD-0040' { doc /*  */ }
  requirement def 'OCS-DM-COM-ICD-0041' { doc /*  */ }
  requirement def 'OCS-DM-COM-ICD-0042' { doc /*  */ }
  requirement def 'OCS-DM-COM-ICD-0043' { doc /*  */ }
  requirement def 'OCS-DM-COM-ICD-0044' { doc /*  */ }
  requirement def 'OCS-DM-COM-ICD-0045' { doc /*  */ }
  requirement def 'OCS-DM-COM-ICD-0046' { doc /*  */ }
  requirement def 'OCS-DM-COM-ICD-0047' { doc /*  */ }
  requirement def 'OCS-DM-COM-ICD-0048' { doc /*  */ }
  requirement def 'OCS-DM-COM-ICD-0049' { doc /*  */ }
  requirement def 'OCS-DM-COM-ICD-0050' { doc /*  */ }
  requirement def 'OCS-DM-COM-ICD-0051' { doc /*  */ }
  requirement def 'OCS-DM-COM-ICD-0052' { doc /*  */ }
  requirement def 'OCS-DM-COM-ICD-0053' { doc /*  */ }
  requirement def 'OCS-DM-COM-ICD-0054' { doc /*  */ }
  requirement def 'OCS-DM-COM-ICD-0055' { doc /*  */ }
  requirement def 'OCS-DM-COM-ICD-0056' { doc /*  */ }
  requirement def 'OCS-EFD-HS-0001' { doc /*  */ }
  requirement def 'OCS-EFD-HS-0002' { doc /*  */ }
  requirement def 'OCS-EFD-HS-0003' { doc /*  */ }
  requirement def 'OCS-EFD-HS-0004' { doc /*  */ }
  requirement def 'OCS-EFD-HS-0005' { doc /*  */ }
  requirement def 'OCS-EFD-HS-0006' { doc /*  */ }
  requirement def 'OCS-EFD-HS-0007' { doc /*  */ }
  requirement def 'OCS-EFD-HS-0008' { doc /*  */ }
  requirement def 'OCS-EFD-HS-0009' { doc /*  */ }
  requirement def 'OCS-EFD-HS-0010' { doc /*  */ }
  requirement def 'OCS-EFD-HS-0011' { doc /*  */ }
  requirement def 'OCS-EFD-HS-0012' { doc /*  */ }
  requirement def 'OCS-EFD-HS-0013' { doc /*  */ }
  requirement def 'OCS-EFD-HS-0014' { doc /*  */ }
  requirement def 'OCS-EFD-HS-0015' { doc /*  */ }
  requirement def 'CA-DM-CON-ICD-0019' { doc /*  */ }
  requirement def 'DMSR-4591' { doc /* Similarly, DMSR-4591 requires that the pipelines fed by Prompt Processing Ingest and producing output via the Telemetry Gateway be down for no more than 24 hours at a time. */ }
  requirement def 'DMSR-3327' { doc /*  */ }
  requirement def 'DMSR-8314' { doc /*  */ }
  requirement def 'DMSR-2490' { doc /*  */ }
  requirement def 'DMSR-2875' { doc /*  */ }
  requirement def 'DMSR-3443' { doc /*  */ }
  requirement def 'DMSR-6640' { doc /*  */ }
  requirement def 'DMSR-8104' { doc /*  */ }
  requirement def 'DMSR-8717' { doc /*  */ }
  requirement def 'DMSR-9849' { doc /*  */ }
  requirement def 'DMSR-1155' { doc /*  */ }
  requirement def 'DMSR-8994' { doc /*  */ }
  requirement def 'DMSR-7327' { doc /*  */ }
  requirement def 'DMSR-1623' { doc /*  */ }
  requirement def 'DMSR-8173' { doc /*  */ }
  requirement def 'OCS-DM-COM-ICD-0003' { doc /*  */ }
  requirement def 'OCS-DM-COM-ICD-0004' { doc /*  */ }
  requirement def 'OCS-DM-COM-ICD-0005' { doc /*  */ }
  requirement def 'OCS-DM-COM-ICD-0006' { doc /*  */ }
  requirement def 'OCS-DM-COM-ICD-0008' { doc /*  */ }
  requirement def 'OCS-DM-COM-ICD-0009' { doc /*  */ }
  requirement def 'OCS-DM-COM-ICD-0012' { doc /*  */ }
  requirement def 'DMSR-9198' { doc /*  */ }
  requirement def 'DM-TS-CON-ICD-0002' { doc /*  */ }
  requirement def 'DM-TS-CON-ICD-0007' { doc /*  */ }
  requirement def 'DMSR-7456' { doc /*  */ }
  requirement def 'DMSR-9004' { doc /*  */ }
  requirement def 'DMSR-1632' { doc /*  */ }
  requirement def 'DMSR-3410' { doc /*  */ }
  requirement def 'OCS-DM-COM-ICD-0007' { doc /*  */ }
  requirement def 'DM-TS-CON-ICD-0006' { doc /*  */ }
  requirement def 'DM-TS-CON-ICD-0011' { doc /*  */ }
  requirement def 'DMSR-3406' { doc /*  */ }
  requirement def 'DMSR-7446' { doc /*  */ }
  requirement def 'DMSR-3446' { doc /*  */ }
  requirement def 'CA-DM-DAQ-ICD-0052' { doc /*  */ }
  requirement def 'DM-TS-CON-ICD-0003' { doc /*  */ }
  requirement def 'DM-TS-CON-ICD-0009' { doc /*  */ }
  requirement def 'DMSR-9791' { doc /*  */ }
  requirement def 'DMSR-1528' { doc /*  */ }
  requirement def 'DM-TS-CON-ICD-0004' { doc /*  */ }
  requirement def 'DMSR-5223' { doc /*  */ }
  requirement def 'DMSR-8983' { doc /*  */ }
  requirement def 'DMSR-9060' { doc /*  */ }
  requirement def 'DMSR-1066' { doc /*  */ }
  requirement def 'DMSR-3448' { doc /*  */ }
  requirement def 'DMSR-6663' { doc /*  */ }
  requirement def 'DMSR-2825' { doc /*  */ }
  requirement def 'DMSR-7271' { doc /*  */ }
  requirement def 'DMSR-4721' { doc /*  */ }
  requirement def 'DMSR-6092' { doc /*  */ }
  requirement def 'DMSR-8956' { doc /*  */ }
  requirement def 'DMSR-6377' { doc /*  */ }
  requirement def 'DMSR-7560' { doc /*  */ }
  requirement def 'DMSR-6108' { doc /*  */ }
  requirement def 'DMSR-1601' { doc /*  */ }
  requirement def 'DMSR-3731' { doc /*  */ }
  requirement def 'DMSR-3011' { doc /*  */ }
  requirement def 'EP-DM-CON-ICD-0004' { doc /*  */ }
  requirement def 'EP-DM-CON-ICD-0009' { doc /*  */ }
  requirement def 'EP-DM-CON-ICD-0019' { doc /*  */ }
  requirement def 'EP-DM-CON-ICD-0021' { doc /*  */ }
  requirement def 'DMSR-4522' { doc /*  */ }
  requirement def 'DMSR-8700' { doc /*  */ }
  requirement def 'DMSR-3757' { doc /*  */ }
  requirement def 'DMSR-3002' { doc /*  */ }
  requirement def 'DMSR-3967' { doc /*  */ }
  requirement def 'DMSR-7545' { doc /*  */ }
  requirement def 'DMSR-3705' { doc /*  */ }
  requirement def 'DMSR-9395' { doc /*  */ }
  requirement def 'DMSR-1602' { doc /*  */ }
  requirement def 'DMSR-9631' { doc /*  */ }
  requirement def 'DMSR-8663' { doc /*  */ }
  requirement def 'DMSR-2203' { doc /*  */ }
  requirement def 'DMSR-5575' { doc /*  */ }
  requirement def 'DMSR-3973' { doc /*  */ }
  requirement def 'DMSR-1851' { doc /*  */ }
  requirement def 'DMSR-3852' { doc /*  */ }
  requirement def 'DMSR-7695' { doc /*  */ }
  requirement def 'DMSR-6131' { doc /*  */ }
  requirement def 'DMSR-2053' { doc /*  */ }
  requirement def 'DMSR-3710' { doc /*  */ }
  requirement def 'DMSR-1961' { doc /*  */ }
  requirement def 'DMSR-3608' { doc /*  */ }
  requirement def 'DMSR-6487' { doc /*  */ }
  requirement def 'DMSR-1919a' { doc /*  */ }
  requirement def 'DMSR-6519a' { doc /*  */ }
  requirement def 'DMSR-3569b' { doc /*  */ }
  requirement def 'DMSR-9570' { doc /*  */ }
  requirement def 'DMSR-1538' { doc /*  */ }
  requirement def 'DMSR-3919' { doc /*  */ }
  requirement def 'DMSR-5731' { doc /*  */ }
  requirement def 'DMSR-3743' { doc /*  */ }
  requirement def 'DMSR-3451' { doc /*  */ }
  requirement def 'DMSR-9495' { doc /*  */ }
  requirement def 'DMSR-9625' { doc /*  */ }
  requirement def 'DMSR-1083' { doc /*  */ }
  requirement def 'DMSR-8804' { doc /*  */ }
  requirement def 'DMSR-9748' { doc /*  */ }
  requirement def 'DMSR-4497' { doc /*  */ }
  requirement def 'DMSR-1376' { doc /*  */ }
  requirement def 'DMSR-5600' { doc /*  */ }
  requirement def 'DMSR-8595' { doc /*  */ }
  requirement def 'DMSR-7328' { doc /*  */ }
  requirement def 'DMSR-1614' { doc /*  */ }
  requirement def 'DMSR-5040' { doc /*  */ }
  requirement def 'DMSR-4348' { doc /*  */ }
  requirement def 'EP-DM-CON-ICD-0034' { doc /*  */ }
  requirement def 'EP-DM-CON-ICD-0036' { doc /*  */ }
  requirement def 'DMSR-5500' { doc /*  */ }
  requirement def 'DMSR-6396' { doc /*  */ }
  requirement def 'DMSR-3233' { doc /*  */ }
  requirement def 'DMSR-1022' { doc /*  */ }
  requirement def 'DMSR-6792' { doc /*  */ }
  requirement def 'DMSR-1431' { doc /*  */ }
  requirement def 'DMSR-9126' { doc /*  */ }
  requirement def 'DMSR-1111' { doc /*  */ }
  requirement def 'DMSR-6155' { doc /*  */ }
  requirement def 'DMSR-1765' { doc /*  */ }
  requirement def 'DMSR-8537' { doc /*  */ }
  requirement def 'DMSR-7201' { doc /*  */ }
  requirement def 'DMSR-7420' { doc /*  */ }
  requirement def 'DMSR-8758' { doc /*  */ }
  requirement def 'DMSR-9056' { doc /*  */ }
  requirement def 'DMSR-4054' { doc /*  */ }
  requirement def 'DMSR-2784' { doc /*  */ }
  requirement def 'DMSR-8704' { doc /*  */ }
  requirement def 'DMSR-8924' { doc /*  */ }
  requirement def 'DMSR-4012' { doc /*  */ }
  requirement def 'DMSR-1060' { doc /*  */ }
  requirement def 'DMSR-8973' { doc /*  */ }
  requirement def 'DMSR-5264' { doc /*  */ }
  requirement def 'DMSR-7938' { doc /*  */ }
  requirement def 'DMSR-8661' { doc /*  */ }
  requirement def 'DMSR-9022' { doc /*  */ }
  requirement def 'DMSR-9439' { doc /*  */ }
  requirement def 'DMSR-3539' { doc /*  */ }
  requirement def 'DMSR-5586' { doc /*  */ }
  requirement def 'DMSR-9307' { doc /*  */ }
  requirement def 'DMSR-9497' { doc /*  */ }
  requirement def 'DMSR-5454' { doc /*  */ }
  requirement def 'DMSR-7791' { doc /*  */ }
  requirement def 'DMSR-6625' { doc /*  */ }
  requirement def 'DMSR-5826' { doc /*  */ }
  requirement def 'DMSR-4291' { doc /*  */ }
  requirement def 'DMSR-3332' { doc /*  */ }
  requirement def 'DMSR-2109' { doc /*  */ }
  requirement def 'DM-TS-CON-ICD-0008' { doc /*  */ }
  requirement def 'DMSR-9725' { doc /*  */ }
  requirement def 'DMSR-7318' { doc /*  */ }
  requirement def 'DMSR-7450' { doc /*  */ }
  requirement def 'EP-DM-CON-ICD-0035' { doc /*  */ }
  requirement def 'DMSR-2240' { doc /*  */ }
  requirement def 'DMSR-4765' { doc /*  */ }
  requirement def 'DMSR-7823' { doc /*  */ }
  requirement def 'DMSR-6799' { doc /*  */ }
  requirement def 'DMSR-6933' { doc /*  */ }
  requirement def 'EP-DM-CON-ICD-0002' { doc /*  */ }
  requirement def 'EP-DM-CON-ICD-0037' { doc /*  */ }
  part def 'Prompt Processing Ingest Def';
  part 'Prompt Processing Ingest' : 'Prompt Processing Ingest Def';
  satisfy 'CA-DM-CON-ICD-0007' by 'Prompt Processing Ingest';
  satisfy 'CA-DM-CON-ICD-0008' by 'Prompt Processing Ingest';
  satisfy 'CA-DM-CON-ICD-0013' by 'Prompt Processing Ingest';
  satisfy 'CA-DM-CON-ICD-0014' by 'Prompt Processing Ingest';
  satisfy 'CA-DM-CON-ICD-0015' by 'Prompt Processing Ingest';
  satisfy 'CA-DM-CON-ICD-0016' by 'Prompt Processing Ingest';
  satisfy 'DMSR-3004' by 'Prompt Processing Ingest';
  satisfy 'DMSR-1570' by 'Prompt Processing Ingest';
  satisfy 'OCS-DM-COM-ICD-0013' by 'Prompt Processing Ingest';
  satisfy 'OCS-DM-COM-ICD-0014' by 'Prompt Processing Ingest';
  satisfy 'OCS-DM-COM-ICD-0015' by 'Prompt Processing Ingest';
  satisfy 'OCS-DM-COM-ICD-0036' by 'Prompt Processing Ingest';
  satisfy 'OCS-DM-COM-ICD-0037' by 'Prompt Processing Ingest';
  satisfy 'OCS-DM-COM-ICD-0038' by 'Prompt Processing Ingest';
  satisfy 'OCS-DM-COM-ICD-0039' by 'Prompt Processing Ingest';
  satisfy 'OCS-DM-COM-ICD-0040' by 'Prompt Processing Ingest';
  satisfy 'OCS-DM-COM-ICD-0046' by 'Prompt Processing Ingest';
  satisfy 'OCS-DM-COM-ICD-0056' by 'Prompt Processing Ingest';
  satisfy 'CA-DM-CON-ICD-0017' by 'Prompt Processing Ingest';
  satisfy 'DM-TS-CON-ICD-0002' by 'Prompt Processing Ingest';
  satisfy 'DM-TS-CON-ICD-0007' by 'Prompt Processing Ingest';
  satisfy 'DMSR-7456' by 'Prompt Processing Ingest';
  satisfy 'DMSR-4591' by 'Prompt Processing Ingest';
  satisfy 'DMSR-9004' by 'Prompt Processing Ingest';
  satisfy 'DMSR-2875' by 'Prompt Processing Ingest';
  satisfy 'DMSR-6640' by 'Prompt Processing Ingest';
  satisfy 'DMSR-1632' by 'Prompt Processing Ingest';
  satisfy 'DMSR-3410' by 'Prompt Processing Ingest';
  satisfy 'DMSR-9849' by 'Prompt Processing Ingest';
  satisfy 'DMSR-8994' by 'Prompt Processing Ingest';
  satisfy 'DMSR-7327' by 'Prompt Processing Ingest';
  satisfy 'DMSR-1623' by 'Prompt Processing Ingest';
  satisfy 'OCS-DM-COM-ICD-0003' by 'Prompt Processing Ingest';
  satisfy 'OCS-DM-COM-ICD-0004' by 'Prompt Processing Ingest';
  satisfy 'OCS-DM-COM-ICD-0007' by 'Prompt Processing Ingest';
  satisfy 'OCS-DM-COM-ICD-0009' by 'Prompt Processing Ingest';
  satisfy 'OCS-DM-COM-ICD-0012' by 'Prompt Processing Ingest';
  part def 'Prompt Processing Def';
  part 'Prompt Processing' : 'Prompt Processing Def';
  satisfy 'CA-DM-CON-ICD-0007' by 'Prompt Processing';
  satisfy 'CA-DM-CON-ICD-0008' by 'Prompt Processing';
  satisfy 'DMSR-2491' by 'Prompt Processing';
  satisfy 'DMSR-3004' by 'Prompt Processing';
  satisfy 'DMSR-1570' by 'Prompt Processing';
  satisfy 'OCS-DM-COM-ICD-0048' by 'Prompt Processing';
  satisfy 'OCS-DM-COM-ICD-0049' by 'Prompt Processing';
  satisfy 'OCS-DM-COM-ICD-0050' by 'Prompt Processing';
  satisfy 'OCS-DM-COM-ICD-0051' by 'Prompt Processing';
  satisfy 'OCS-DM-COM-ICD-0052' by 'Prompt Processing';
  satisfy 'OCS-DM-COM-ICD-0056' by 'Prompt Processing';
  satisfy 'DM-TS-CON-ICD-0002' by 'Prompt Processing';
  satisfy 'DM-TS-CON-ICD-0006' by 'Prompt Processing';
  satisfy 'DM-TS-CON-ICD-0007' by 'Prompt Processing';
  satisfy 'DM-TS-CON-ICD-0011' by 'Prompt Processing';
  satisfy 'DMSR-7456' by 'Prompt Processing';
  satisfy 'DMSR-4591' by 'Prompt Processing';
  satisfy 'DMSR-2875' by 'Prompt Processing';
  satisfy 'DMSR-6640' by 'Prompt Processing';
  satisfy 'DMSR-1632' by 'Prompt Processing';
  satisfy 'DMSR-3410' by 'Prompt Processing';
  satisfy 'DMSR-9849' by 'Prompt Processing';
  satisfy 'DMSR-3406' by 'Prompt Processing';
  satisfy 'DMSR-8994' by 'Prompt Processing';
  satisfy 'DMSR-1623' by 'Prompt Processing';
  satisfy 'DMSR-7446' by 'Prompt Processing';
  satisfy 'DMSR-3446' by 'Prompt Processing';
  satisfy 'DMSR-8173' by 'Prompt Processing';
  satisfy 'OCS-DM-COM-ICD-0007' by 'Prompt Processing';
  part def 'Telemetry Gateway Def';
  part 'Telemetry Gateway' : 'Telemetry Gateway Def';
  satisfy 'CA-DM-CON-ICD-0007' by 'Telemetry Gateway';
  satisfy 'CA-DM-CON-ICD-0008' by 'Telemetry Gateway';
  satisfy 'OCS-DM-COM-ICD-0017' by 'Telemetry Gateway';
  satisfy 'OCS-DM-COM-ICD-0018' by 'Telemetry Gateway';
  satisfy 'OCS-DM-COM-ICD-0019' by 'Telemetry Gateway';
  satisfy 'OCS-DM-COM-ICD-0020' by 'Telemetry Gateway';
  satisfy 'OCS-DM-COM-ICD-0021' by 'Telemetry Gateway';
  satisfy 'OCS-DM-COM-ICD-0022' by 'Telemetry Gateway';
  satisfy 'OCS-DM-COM-ICD-0043' by 'Telemetry Gateway';
  satisfy 'OCS-DM-COM-ICD-0044' by 'Telemetry Gateway';
  satisfy 'OCS-DM-COM-ICD-0045' by 'Telemetry Gateway';
  satisfy 'OCS-DM-COM-ICD-0046' by 'Telemetry Gateway';
  satisfy 'OCS-DM-COM-ICD-0047' by 'Telemetry Gateway';
  satisfy 'OCS-DM-COM-ICD-0048' by 'Telemetry Gateway';
  satisfy 'OCS-DM-COM-ICD-0049' by 'Telemetry Gateway';
  satisfy 'OCS-DM-COM-ICD-0050' by 'Telemetry Gateway';
  satisfy 'OCS-DM-COM-ICD-0051' by 'Telemetry Gateway';
  satisfy 'OCS-DM-COM-ICD-0052' by 'Telemetry Gateway';
  satisfy 'OCS-DM-COM-ICD-0053' by 'Telemetry Gateway';
  satisfy 'OCS-DM-COM-ICD-0054' by 'Telemetry Gateway';
  satisfy 'OCS-DM-COM-ICD-0055' by 'Telemetry Gateway';
  satisfy 'OCS-DM-COM-ICD-0056' by 'Telemetry Gateway';
  satisfy 'DM-TS-CON-ICD-0002' by 'Telemetry Gateway';
  satisfy 'DM-TS-CON-ICD-0004' by 'Telemetry Gateway';
  satisfy 'DM-TS-CON-ICD-0006' by 'Telemetry Gateway';
  satisfy 'DM-TS-CON-ICD-0007' by 'Telemetry Gateway';
  satisfy 'DM-TS-CON-ICD-0011' by 'Telemetry Gateway';
  part def 'Prompt Base Enclave Def';
  part 'Prompt Base Enclave' : 'Prompt Base Enclave Def';
  satisfy 'CA-DM-CON-ICD-0007' by 'Prompt Base Enclave';
  satisfy 'CA-DM-CON-ICD-0008' by 'Prompt Base Enclave';
  satisfy 'CA-DM-CON-ICD-0013' by 'Prompt Base Enclave';
  satisfy 'CA-DM-CON-ICD-0014' by 'Prompt Base Enclave';
  satisfy 'CA-DM-CON-ICD-0015' by 'Prompt Base Enclave';
  satisfy 'CA-DM-CON-ICD-0016' by 'Prompt Base Enclave';
  satisfy 'CA-DM-CON-ICD-0017' by 'Prompt Base Enclave';
  satisfy 'DMSR-8525' by 'Prompt Base Enclave';
  satisfy 'DMSR-5909' by 'Prompt Base Enclave';
  satisfy 'DMSR-1570' by 'Prompt Base Enclave';
  satisfy 'DMSR-8254' by 'Prompt Base Enclave';
  satisfy 'OCS-DM-COM-ICD-0017' by 'Prompt Base Enclave';
  satisfy 'OCS-DM-COM-ICD-0018' by 'Prompt Base Enclave';
  satisfy 'OCS-DM-COM-ICD-0019' by 'Prompt Base Enclave';
  satisfy 'OCS-DM-COM-ICD-0020' by 'Prompt Base Enclave';
  satisfy 'OCS-DM-COM-ICD-0021' by 'Prompt Base Enclave';
  satisfy 'OCS-DM-COM-ICD-0022' by 'Prompt Base Enclave';
  satisfy 'OCS-DM-COM-ICD-0025' by 'Prompt Base Enclave';
  satisfy 'OCS-DM-COM-ICD-0026' by 'Prompt Base Enclave';
  satisfy 'OCS-DM-COM-ICD-0027' by 'Prompt Base Enclave';
  satisfy 'OCS-DM-COM-ICD-0028' by 'Prompt Base Enclave';
  satisfy 'OCS-DM-COM-ICD-0030' by 'Prompt Base Enclave';
  satisfy 'CA-DM-CON-ICD-0019' by 'Prompt Base Enclave';
  satisfy 'DM-TS-CON-ICD-0002' by 'Prompt Base Enclave';
  satisfy 'DM-TS-CON-ICD-0003' by 'Prompt Base Enclave';
  satisfy 'DM-TS-CON-ICD-0004' by 'Prompt Base Enclave';
  satisfy 'DM-TS-CON-ICD-0006' by 'Prompt Base Enclave';
  satisfy 'DM-TS-CON-ICD-0007' by 'Prompt Base Enclave';
  satisfy 'DM-TS-CON-ICD-0009' by 'Prompt Base Enclave';
  satisfy 'DM-TS-CON-ICD-0011' by 'Prompt Base Enclave';
  satisfy 'DMSR-7456' by 'Prompt Base Enclave';
  satisfy 'DMSR-4591' by 'Prompt Base Enclave';
  satisfy 'DMSR-3327' by 'Prompt Base Enclave';
  satisfy 'DMSR-8314' by 'Prompt Base Enclave';
  satisfy 'DMSR-9004' by 'Prompt Base Enclave';
  satisfy 'DMSR-2490' by 'Prompt Base Enclave';
  satisfy 'DMSR-8983' by 'Prompt Base Enclave';
  satisfy 'DMSR-9060' by 'Prompt Base Enclave';
  satisfy 'DMSR-1066' by 'Prompt Base Enclave';
  satisfy 'DMSR-2875' by 'Prompt Base Enclave';
  satisfy 'DMSR-3448' by 'Prompt Base Enclave';
  satisfy 'DMSR-9791' by 'Prompt Base Enclave';
  satisfy 'DMSR-3443' by 'Prompt Base Enclave';
  part def 'Archiving Def';
  part 'Archiving' : 'Archiving Def';
  satisfy 'CA-DM-CON-ICD-0013' by 'Archiving';
  satisfy 'CA-DM-CON-ICD-0014' by 'Archiving';
  satisfy 'CA-DM-CON-ICD-0015' by 'Archiving';
  satisfy 'CA-DM-CON-ICD-0016' by 'Archiving';
  satisfy 'CA-DM-CON-ICD-0017' by 'Archiving';
  satisfy 'DMSR-8525' by 'Archiving';
  satisfy 'DMSR-1570' by 'Archiving';
  satisfy 'OCS-DM-COM-ICD-0013' by 'Archiving';
  satisfy 'OCS-DM-COM-ICD-0014' by 'Archiving';
  satisfy 'OCS-DM-COM-ICD-0015' by 'Archiving';
  satisfy 'OCS-DM-COM-ICD-0025' by 'Archiving';
  satisfy 'OCS-DM-COM-ICD-0026' by 'Archiving';
  satisfy 'OCS-DM-COM-ICD-0027' by 'Archiving';
  satisfy 'OCS-DM-COM-ICD-0028' by 'Archiving';
  satisfy 'OCS-DM-COM-ICD-0029' by 'Archiving';
  satisfy 'OCS-DM-COM-ICD-0030' by 'Archiving';
  satisfy 'OCS-DM-COM-ICD-0032' by 'Archiving';
  satisfy 'OCS-DM-COM-ICD-0033' by 'Archiving';
  satisfy 'OCS-DM-COM-ICD-0034' by 'Archiving';
  satisfy 'OCS-DM-COM-ICD-0036' by 'Archiving';
  satisfy 'OCS-DM-COM-ICD-0037' by 'Archiving';
  satisfy 'OCS-DM-COM-ICD-0038' by 'Archiving';
  satisfy 'OCS-DM-COM-ICD-0039' by 'Archiving';
  satisfy 'OCS-DM-COM-ICD-0040' by 'Archiving';
  satisfy 'OCS-DM-COM-ICD-0041' by 'Archiving';
  satisfy 'OCS-DM-COM-ICD-0042' by 'Archiving';
  satisfy 'OCS-DM-COM-ICD-0043' by 'Archiving';
  satisfy 'OCS-DM-COM-ICD-0044' by 'Archiving';
  satisfy 'OCS-DM-COM-ICD-0045' by 'Archiving';
  satisfy 'OCS-DM-COM-ICD-0055' by 'Archiving';
  satisfy 'OCS-EFD-HS-0001' by 'Archiving';
  satisfy 'OCS-EFD-HS-0002' by 'Archiving';
  satisfy 'OCS-EFD-HS-0003' by 'Archiving';
  satisfy 'OCS-EFD-HS-0004' by 'Archiving';
  satisfy 'OCS-EFD-HS-0005' by 'Archiving';
  satisfy 'OCS-EFD-HS-0006' by 'Archiving';
  satisfy 'OCS-EFD-HS-0007' by 'Archiving';
  satisfy 'OCS-EFD-HS-0008' by 'Archiving';
  satisfy 'OCS-EFD-HS-0009' by 'Archiving';
  satisfy 'OCS-EFD-HS-0010' by 'Archiving';
  satisfy 'OCS-EFD-HS-0011' by 'Archiving';
  satisfy 'OCS-EFD-HS-0012' by 'Archiving';
  satisfy 'OCS-EFD-HS-0013' by 'Archiving';
  satisfy 'OCS-EFD-HS-0014' by 'Archiving';
  satisfy 'OCS-EFD-HS-0015' by 'Archiving';
  satisfy 'CA-DM-CON-ICD-0019' by 'Archiving';
  satisfy 'DMSR-4591' by 'Archiving';
  satisfy 'DMSR-3327' by 'Archiving';
  satisfy 'DMSR-8314' by 'Archiving';
  satisfy 'DMSR-2490' by 'Archiving';
  satisfy 'DMSR-2875' by 'Archiving';
  satisfy 'DMSR-3443' by 'Archiving';
  satisfy 'DMSR-6640' by 'Archiving';
  satisfy 'DMSR-8104' by 'Archiving';
  part def 'Image Ingest and Processing Def';
  part 'Image Ingest and Processing' : 'Image Ingest and Processing Def';
  satisfy 'CA-DM-CON-ICD-0013' by 'Image Ingest and Processing';
  satisfy 'CA-DM-CON-ICD-0014' by 'Image Ingest and Processing';
  satisfy 'CA-DM-CON-ICD-0015' by 'Image Ingest and Processing';
  satisfy 'CA-DM-CON-ICD-0016' by 'Image Ingest and Processing';
  satisfy 'CA-DM-CON-ICD-0017' by 'Image Ingest and Processing';
  satisfy 'DMSR-8525' by 'Image Ingest and Processing';
  satisfy 'DMSR-3004' by 'Image Ingest and Processing';
  satisfy 'DMSR-1570' by 'Image Ingest and Processing';
  satisfy 'OCS-DM-COM-ICD-0013' by 'Image Ingest and Processing';
  satisfy 'OCS-DM-COM-ICD-0014' by 'Image Ingest and Processing';
  satisfy 'OCS-DM-COM-ICD-0015' by 'Image Ingest and Processing';
  satisfy 'OCS-DM-COM-ICD-0032' by 'Image Ingest and Processing';
  satisfy 'OCS-DM-COM-ICD-0036' by 'Image Ingest and Processing';
  satisfy 'OCS-DM-COM-ICD-0037' by 'Image Ingest and Processing';
  satisfy 'OCS-DM-COM-ICD-0038' by 'Image Ingest and Processing';
  satisfy 'OCS-DM-COM-ICD-0039' by 'Image Ingest and Processing';
  satisfy 'OCS-DM-COM-ICD-0040' by 'Image Ingest and Processing';
  satisfy 'OCS-DM-COM-ICD-0043' by 'Image Ingest and Processing';
  satisfy 'OCS-DM-COM-ICD-0044' by 'Image Ingest and Processing';
  satisfy 'OCS-DM-COM-ICD-0045' by 'Image Ingest and Processing';
  satisfy 'OCS-DM-COM-ICD-0055' by 'Image Ingest and Processing';
  satisfy 'OCS-DM-COM-ICD-0056' by 'Image Ingest and Processing';
  satisfy 'CA-DM-CON-ICD-0019' by 'Image Ingest and Processing';
  satisfy 'DM-TS-CON-ICD-0002' by 'Image Ingest and Processing';
  satisfy 'DM-TS-CON-ICD-0007' by 'Image Ingest and Processing';
  satisfy 'DMSR-7456' by 'Image Ingest and Processing';
  satisfy 'DMSR-4591' by 'Image Ingest and Processing';
  satisfy 'DMSR-3327' by 'Image Ingest and Processing';
  satisfy 'DMSR-8314' by 'Image Ingest and Processing';
  satisfy 'DMSR-9004' by 'Image Ingest and Processing';
  satisfy 'DMSR-2490' by 'Image Ingest and Processing';
  satisfy 'DMSR-2875' by 'Image Ingest and Processing';
  satisfy 'DMSR-8104' by 'Image Ingest and Processing';
  satisfy 'DMSR-8717' by 'Image Ingest and Processing';
  satisfy 'DMSR-1632' by 'Image Ingest and Processing';
  satisfy 'DMSR-3410' by 'Image Ingest and Processing';
  satisfy 'DMSR-9849' by 'Image Ingest and Processing';
  satisfy 'DMSR-1155' by 'Image Ingest and Processing';
  satisfy 'DMSR-8994' by 'Image Ingest and Processing';
  satisfy 'DMSR-7327' by 'Image Ingest and Processing';
  satisfy 'DMSR-1623' by 'Image Ingest and Processing';
  satisfy 'DMSR-7446' by 'Image Ingest and Processing';
  satisfy 'DMSR-3446' by 'Image Ingest and Processing';
  satisfy 'DMSR-8173' by 'Image Ingest and Processing';
  satisfy 'OCS-DM-COM-ICD-0003' by 'Image Ingest and Processing';
  satisfy 'OCS-DM-COM-ICD-0004' by 'Image Ingest and Processing';
  satisfy 'OCS-DM-COM-ICD-0005' by 'Image Ingest and Processing';
  satisfy 'OCS-DM-COM-ICD-0006' by 'Image Ingest and Processing';
  satisfy 'OCS-DM-COM-ICD-0007' by 'Image Ingest and Processing';
  satisfy 'OCS-DM-COM-ICD-0009' by 'Image Ingest and Processing';
  satisfy 'OCS-DM-COM-ICD-0012' by 'Image Ingest and Processing';
  part def 'Archive Base Enclave Def';
  part 'Archive Base Enclave' : 'Archive Base Enclave Def';
  satisfy 'CA-DM-CON-ICD-0017' by 'Archive Base Enclave';
  satisfy 'DMSR-7692' by 'Archive Base Enclave';
  satisfy 'DMSR-3617' by 'Archive Base Enclave';
  satisfy 'DMSR-6475' by 'Archive Base Enclave';
  satisfy 'DMSR-8494' by 'Archive Base Enclave';
  satisfy 'DMSR-3337' by 'Archive Base Enclave';
  satisfy 'DMSR-3004' by 'Archive Base Enclave';
  satisfy 'DMSR-5909' by 'Archive Base Enclave';
  satisfy 'DMSR-1570' by 'Archive Base Enclave';
  satisfy 'DMSR-8254' by 'Archive Base Enclave';
  satisfy 'DMSR-9563' by 'Archive Base Enclave';
  satisfy 'DMSR-6206' by 'Archive Base Enclave';
  satisfy 'DMSR-2551' by 'Archive Base Enclave';
  satisfy 'DMSR-1436' by 'Archive Base Enclave';
  satisfy 'OCS-DM-COM-ICD-0027' by 'Archive Base Enclave';
  satisfy 'OCS-DM-COM-ICD-0028' by 'Archive Base Enclave';
  satisfy 'OCS-DM-COM-ICD-0029' by 'Archive Base Enclave';
  satisfy 'OCS-DM-COM-ICD-0030' by 'Archive Base Enclave';
  satisfy 'CA-DM-CON-ICD-0019' by 'Archive Base Enclave';
  satisfy 'DM-TS-CON-ICD-0003' by 'Archive Base Enclave';
  satisfy 'DMSR-7456' by 'Archive Base Enclave';
  satisfy 'DMSR-6396' by 'Archive Base Enclave';
  satisfy 'DMSR-3233' by 'Archive Base Enclave';
  satisfy 'DMSR-1022' by 'Archive Base Enclave';
  satisfy 'DMSR-3443' by 'Archive Base Enclave';
  satisfy 'DMSR-8924' by 'Archive Base Enclave';
  part def 'Archive NCSA Enclave Def';
  part 'Archive NCSA Enclave' : 'Archive NCSA Enclave Def';
  satisfy 'CA-DM-CON-ICD-0017' by 'Archive NCSA Enclave';
  satisfy 'DMSR-7692' by 'Archive NCSA Enclave';
  satisfy 'DMSR-3617' by 'Archive NCSA Enclave';
  satisfy 'DMSR-6475' by 'Archive NCSA Enclave';
  satisfy 'DMSR-8494' by 'Archive NCSA Enclave';
  satisfy 'DMSR-3337' by 'Archive NCSA Enclave';
  satisfy 'DMSR-3004' by 'Archive NCSA Enclave';
  satisfy 'DMSR-5909' by 'Archive NCSA Enclave';
  satisfy 'DMSR-1570' by 'Archive NCSA Enclave';
  satisfy 'DMSR-3565' by 'Archive NCSA Enclave';
  satisfy 'DMSR-9563' by 'Archive NCSA Enclave';
  satisfy 'DMSR-6206' by 'Archive NCSA Enclave';
  satisfy 'DMSR-2551' by 'Archive NCSA Enclave';
  satisfy 'DMSR-1436' by 'Archive NCSA Enclave';
  satisfy 'OCS-DM-COM-ICD-0027' by 'Archive NCSA Enclave';
  satisfy 'OCS-DM-COM-ICD-0028' by 'Archive NCSA Enclave';
  satisfy 'OCS-DM-COM-ICD-0029' by 'Archive NCSA Enclave';
  satisfy 'OCS-DM-COM-ICD-0030' by 'Archive NCSA Enclave';
  satisfy 'CA-DM-CON-ICD-0019' by 'Archive NCSA Enclave';
  satisfy 'DM-TS-CON-ICD-0003' by 'Archive NCSA Enclave';
  satisfy 'DMSR-7456' by 'Archive NCSA Enclave';
  satisfy 'DMSR-6396' by 'Archive NCSA Enclave';
  satisfy 'DMSR-3233' by 'Archive NCSA Enclave';
  satisfy 'DMSR-1022' by 'Archive NCSA Enclave';
  satisfy 'DMSR-3443' by 'Archive NCSA Enclave';
  satisfy 'DMSR-8924' by 'Archive NCSA Enclave';
  satisfy 'DMSR-6640' by 'Archive NCSA Enclave';
  satisfy 'DMSR-6663' by 'Archive NCSA Enclave';
  satisfy 'DMSR-3757' by 'Archive NCSA Enclave';
  satisfy 'DMSR-3967' by 'Archive NCSA Enclave';
  satisfy 'DMSR-4012' by 'Archive NCSA Enclave';
  satisfy 'DMSR-1060' by 'Archive NCSA Enclave';
  satisfy 'DMSR-7545' by 'Archive NCSA Enclave';
  satisfy 'DMSR-6155' by 'Archive NCSA Enclave';
  satisfy 'DMSR-3705' by 'Archive NCSA Enclave';
  satisfy 'DMSR-1765' by 'Archive NCSA Enclave';
  satisfy 'DMSR-9395' by 'Archive NCSA Enclave';
  satisfy 'DMSR-8537' by 'Archive NCSA Enclave';
  satisfy 'DMSR-8973' by 'Archive NCSA Enclave';
  satisfy 'DMSR-1632' by 'Archive NCSA Enclave';
  satisfy 'DMSR-1602' by 'Archive NCSA Enclave';
  satisfy 'DMSR-9631' by 'Archive NCSA Enclave';
  satisfy 'DMSR-1155' by 'Archive NCSA Enclave';
  satisfy 'DMSR-3973' by 'Archive NCSA Enclave';
  satisfy 'DMSR-3406' by 'Archive NCSA Enclave';
  satisfy 'DMSR-8994' by 'Archive NCSA Enclave';
  satisfy 'DMSR-3852' by 'Archive NCSA Enclave';
  satisfy 'DMSR-1623' by 'Archive NCSA Enclave';
  satisfy 'DMSR-7695' by 'Archive NCSA Enclave';
  satisfy 'DMSR-5600' by 'Archive NCSA Enclave';
  satisfy 'DMSR-3446' by 'Archive NCSA Enclave';
  satisfy 'DMSR-6131' by 'Archive NCSA Enclave';
  satisfy 'DMSR-2053' by 'Archive NCSA Enclave';
  satisfy 'DMSR-3710' by 'Archive NCSA Enclave';
  satisfy 'DMSR-1961' by 'Archive NCSA Enclave';
  satisfy 'DMSR-9570' by 'Archive NCSA Enclave';
  satisfy 'DMSR-1538' by 'Archive NCSA Enclave';
  satisfy 'DMSR-3608' by 'Archive NCSA Enclave';
  satisfy 'DMSR-6487' by 'Archive NCSA Enclave';
  part def 'Prompt NCSA Enclave Def';
  part 'Prompt NCSA Enclave' : 'Prompt NCSA Enclave Def';
  satisfy 'CA-DM-CON-ICD-0017' by 'Prompt NCSA Enclave';
  satisfy 'DMSR-2491' by 'Prompt NCSA Enclave';
  satisfy 'DMSR-7692' by 'Prompt NCSA Enclave';
  satisfy 'DMSR-9449' by 'Prompt NCSA Enclave';
  satisfy 'DMSR-1786' by 'Prompt NCSA Enclave';
  satisfy 'DMSR-2005' by 'Prompt NCSA Enclave';
  satisfy 'DMSR-3004' by 'Prompt NCSA Enclave';
  satisfy 'DMSR-5909' by 'Prompt NCSA Enclave';
  satisfy 'DMSR-1570' by 'Prompt NCSA Enclave';
  satisfy 'DMSR-3565' by 'Prompt NCSA Enclave';
  satisfy 'DMSR-6206' by 'Prompt NCSA Enclave';
  satisfy 'DMSR-6023' by 'Prompt NCSA Enclave';
  satisfy 'DMSR-5729' by 'Prompt NCSA Enclave';
  satisfy 'CA-DM-CON-ICD-0019' by 'Prompt NCSA Enclave';
  satisfy 'DMSR-7456' by 'Prompt NCSA Enclave';
  satisfy 'DMSR-4591' by 'Prompt NCSA Enclave';
  satisfy 'DMSR-6396' by 'Prompt NCSA Enclave';
  satisfy 'DMSR-3233' by 'Prompt NCSA Enclave';
  satisfy 'DMSR-1022' by 'Prompt NCSA Enclave';
  satisfy 'DMSR-8983' by 'Prompt NCSA Enclave';
  satisfy 'DMSR-9060' by 'Prompt NCSA Enclave';
  satisfy 'DMSR-1066' by 'Prompt NCSA Enclave';
  satisfy 'DMSR-2875' by 'Prompt NCSA Enclave';
  satisfy 'DMSR-3448' by 'Prompt NCSA Enclave';
  satisfy 'DMSR-9791' by 'Prompt NCSA Enclave';
  satisfy 'DMSR-3443' by 'Prompt NCSA Enclave';
  satisfy 'DMSR-6640' by 'Prompt NCSA Enclave';
  satisfy 'DMSR-8104' by 'Prompt NCSA Enclave';
  satisfy 'DMSR-3757' by 'Prompt NCSA Enclave';
  satisfy 'DMSR-3967' by 'Prompt NCSA Enclave';
  satisfy 'DMSR-7545' by 'Prompt NCSA Enclave';
  satisfy 'DMSR-6155' by 'Prompt NCSA Enclave';
  satisfy 'DMSR-3705' by 'Prompt NCSA Enclave';
  satisfy 'DMSR-1765' by 'Prompt NCSA Enclave';
  satisfy 'DMSR-9395' by 'Prompt NCSA Enclave';
  satisfy 'DMSR-8537' by 'Prompt NCSA Enclave';
  satisfy 'DMSR-1632' by 'Prompt NCSA Enclave';
  satisfy 'DMSR-1155' by 'Prompt NCSA Enclave';
  satisfy 'DMSR-8994' by 'Prompt NCSA Enclave';
  satisfy 'DMSR-3852' by 'Prompt NCSA Enclave';
  satisfy 'DMSR-1623' by 'Prompt NCSA Enclave';
  satisfy 'DMSR-8758' by 'Prompt NCSA Enclave';
  satisfy 'DMSR-5586' by 'Prompt NCSA Enclave';
  satisfy 'DMSR-7446' by 'Prompt NCSA Enclave';
  satisfy 'DMSR-3446' by 'Prompt NCSA Enclave';
  part def 'Alert Distribution Def';
  part 'Alert Distribution' : 'Alert Distribution Def';
  satisfy 'DMSR-2491' by 'Alert Distribution';
  satisfy 'DMSR-5909' by 'Alert Distribution';
  satisfy 'DMSR-1570' by 'Alert Distribution';
  satisfy 'DMSR-2058' by 'Alert Distribution';
  satisfy 'DMSR-5729' by 'Alert Distribution';
  satisfy 'DMSR-7456' by 'Alert Distribution';
  satisfy 'DMSR-4591' by 'Alert Distribution';
  satisfy 'DMSR-6640' by 'Alert Distribution';
  satisfy 'DMSR-8994' by 'Alert Distribution';
  satisfy 'DMSR-1623' by 'Alert Distribution';
  satisfy 'DMSR-5223' by 'Alert Distribution';
  part def 'Alert Distribution SW Def';
  part 'Alert Distribution SW' : 'Alert Distribution SW Def';
  satisfy 'DMSR-2491' by 'Alert Distribution SW';
  satisfy 'DMSR-5909' by 'Alert Distribution SW';
  satisfy 'DMSR-1570' by 'Alert Distribution SW';
  satisfy 'DMSR-2058' by 'Alert Distribution SW';
  satisfy 'DMSR-5729' by 'Alert Distribution SW';
  satisfy 'OCS-DM-COM-ICD-0048' by 'Alert Distribution SW';
  satisfy 'DMSR-7456' by 'Alert Distribution SW';
  satisfy 'DMSR-4591' by 'Alert Distribution SW';
  satisfy 'DMSR-6640' by 'Alert Distribution SW';
  satisfy 'DMSR-8994' by 'Alert Distribution SW';
  satisfy 'DMSR-1623' by 'Alert Distribution SW';
  satisfy 'DMSR-5223' by 'Alert Distribution SW';
  part def 'Alert Production Def';
  part 'Alert Production' : 'Alert Production Def';
  satisfy 'DMSR-2491' by 'Alert Production';
  satisfy 'DMSR-6406' by 'Alert Production';
  satisfy 'DMSR-7692' by 'Alert Production';
  satisfy 'DMSR-9449' by 'Alert Production';
  satisfy 'DMSR-1786' by 'Alert Production';
  satisfy 'DMSR-2005' by 'Alert Production';
  satisfy 'DMSR-6206' by 'Alert Production';
  satisfy 'DMSR-6023' by 'Alert Production';
  satisfy 'DMSR-9580' by 'Alert Production';
  satisfy 'OCS-DM-COM-ICD-0049' by 'Alert Production';
  satisfy 'OCS-DM-COM-ICD-0050' by 'Alert Production';
  satisfy 'OCS-DM-COM-ICD-0051' by 'Alert Production';
  satisfy 'OCS-DM-COM-ICD-0052' by 'Alert Production';
  satisfy 'DMSR-7456' by 'Alert Production';
  satisfy 'DMSR-5500' by 'Alert Production';
  satisfy 'DMSR-6396' by 'Alert Production';
  satisfy 'DMSR-3233' by 'Alert Production';
  satisfy 'DMSR-1022' by 'Alert Production';
  satisfy 'DMSR-6792' by 'Alert Production';
  satisfy 'DMSR-1431' by 'Alert Production';
  satisfy 'DMSR-9126' by 'Alert Production';
  satisfy 'DMSR-1111' by 'Alert Production';
  satisfy 'DMSR-9060' by 'Alert Production';
  satisfy 'DMSR-3967' by 'Alert Production';
  satisfy 'DMSR-7545' by 'Alert Production';
  satisfy 'DMSR-6155' by 'Alert Production';
  satisfy 'DMSR-3705' by 'Alert Production';
  satisfy 'DMSR-1765' by 'Alert Production';
  satisfy 'DMSR-8537' by 'Alert Production';
  satisfy 'DMSR-7201' by 'Alert Production';
  satisfy 'DMSR-7420' by 'Alert Production';
  satisfy 'DMSR-8956' by 'Alert Production';
  satisfy 'DMSR-3406' by 'Alert Production';
  satisfy 'DMSR-3852' by 'Alert Production';
  satisfy 'DMSR-8758' by 'Alert Production';
  satisfy 'DMSR-7446' by 'Alert Production';
  satisfy 'DMSR-5600' by 'Alert Production';
  satisfy 'DMSR-3446' by 'Alert Production';
  satisfy 'DMSR-7328' by 'Alert Production';
  part def 'Data Release Production Def';
  part 'Data Release Production' : 'Data Release Production Def';
  satisfy 'DMSR-6406' by 'Data Release Production';
  satisfy 'DMSR-1591' by 'Data Release Production';
  satisfy 'DMSR-3753' by 'Data Release Production';
  satisfy 'DMSR-3770' by 'Data Release Production';
  satisfy 'DMSR-9580' by 'Data Release Production';
  satisfy 'DMSR-8635' by 'Data Release Production';
  satisfy 'DMSR-9850' by 'Data Release Production';
  part def 'Science Pipelines Libraries Def';
  part 'Science Pipelines Libraries' : 'Science Pipelines Libraries Def';
  satisfy 'DMSR-6406' by 'Science Pipelines Libraries';
  satisfy 'DM-TS-CON-ICD-0008' by 'Science Pipelines Libraries';
  satisfy 'DMSR-6792' by 'Science Pipelines Libraries';
  satisfy 'DMSR-1431' by 'Science Pipelines Libraries';
  satisfy 'DMSR-9126' by 'Science Pipelines Libraries';
  satisfy 'DMSR-1111' by 'Science Pipelines Libraries';
  satisfy 'DMSR-9725' by 'Science Pipelines Libraries';
  satisfy 'DMSR-8956' by 'Science Pipelines Libraries';
  satisfy 'DMSR-7318' by 'Science Pipelines Libraries';
  part def 'Science Plugins Def';
  part 'Science Plugins' : 'Science Plugins Def';
  satisfy 'DMSR-1478' by 'Science Plugins';
  satisfy 'DMSR-3563' by 'Science Plugins';
  satisfy 'DMSR-7763' by 'Science Plugins';
  satisfy 'DMSR-5876' by 'Science Plugins';
  satisfy 'DMSR-1963' by 'Science Plugins';
  satisfy 'DMSR-3004' by 'Science Plugins';
  satisfy 'DMSR-3997' by 'Science Plugins';
  satisfy 'DMSR-3448' by 'Science Plugins';
  satisfy 'DMSR-9791' by 'Science Plugins';
  satisfy 'DMSR-8717' by 'Science Plugins';
  satisfy 'DMSR-3332' by 'Science Plugins';
  satisfy 'DMSR-2109' by 'Science Plugins';
  satisfy 'DMSR-1528' by 'Science Plugins';
  satisfy 'DMSR-8956' by 'Science Plugins';
  part def 'Science Pipelines Distribution Def';
  part 'Science Pipelines Distribution' : 'Science Pipelines Distribution Def';
  satisfy 'DMSR-1478' by 'Science Pipelines Distribution';
  satisfy 'DMSR-3563' by 'Science Pipelines Distribution';
  satisfy 'DMSR-7763' by 'Science Pipelines Distribution';
  satisfy 'DMSR-5876' by 'Science Pipelines Distribution';
  satisfy 'DMSR-1963' by 'Science Pipelines Distribution';
  satisfy 'DMSR-3997' by 'Science Pipelines Distribution';
  satisfy 'CA-DM-DAQ-ICD-0052' by 'Science Pipelines Distribution';
  satisfy 'DMSR-8717' by 'Science Pipelines Distribution';
  satisfy 'DMSR-3332' by 'Science Pipelines Distribution';
  satisfy 'DMSR-2109' by 'Science Pipelines Distribution';
  satisfy 'DMSR-1528' by 'Science Pipelines Distribution';
  satisfy 'DMSR-8956' by 'Science Pipelines Distribution';
  part def 'Offline Production Enclave Def';
  part 'Offline Production Enclave' : 'Offline Production Enclave Def';
  satisfy 'DMSR-1478' by 'Offline Production Enclave';
  satisfy 'DMSR-3563' by 'Offline Production Enclave';
  satisfy 'DMSR-7763' by 'Offline Production Enclave';
  satisfy 'DMSR-5876' by 'Offline Production Enclave';
  satisfy 'DMSR-1963' by 'Offline Production Enclave';
  satisfy 'DMSR-3004' by 'Offline Production Enclave';
  satisfy 'DMSR-3997' by 'Offline Production Enclave';
  satisfy 'DMSR-5909' by 'Offline Production Enclave';
  satisfy 'DMSR-1570' by 'Offline Production Enclave';
  satisfy 'DMSR-3565' by 'Offline Production Enclave';
  satisfy 'DMSR-9563' by 'Offline Production Enclave';
  satisfy 'DMSR-1591' by 'Offline Production Enclave';
  satisfy 'DMSR-3753' by 'Offline Production Enclave';
  satisfy 'DMSR-2551' by 'Offline Production Enclave';
  satisfy 'DMSR-8635' by 'Offline Production Enclave';
  satisfy 'DMSR-9308' by 'Offline Production Enclave';
  satisfy 'DM-TS-CON-ICD-0003' by 'Offline Production Enclave';
  satisfy 'DMSR-7456' by 'Offline Production Enclave';
  satisfy 'DMSR-4591' by 'Offline Production Enclave';
  satisfy 'DMSR-9056' by 'Offline Production Enclave';
  satisfy 'DMSR-4054' by 'Offline Production Enclave';
  satisfy 'DMSR-2784' by 'Offline Production Enclave';
  satisfy 'DMSR-8704' by 'Offline Production Enclave';
  satisfy 'DMSR-8924' by 'Offline Production Enclave';
  satisfy 'DMSR-6640' by 'Offline Production Enclave';
  satisfy 'DMSR-6663' by 'Offline Production Enclave';
  satisfy 'DMSR-3757' by 'Offline Production Enclave';
  satisfy 'DMSR-4012' by 'Offline Production Enclave';
  satisfy 'DMSR-1060' by 'Offline Production Enclave';
  satisfy 'DMSR-8973' by 'Offline Production Enclave';
  satisfy 'DMSR-7938' by 'Offline Production Enclave';
  satisfy 'DMSR-8661' by 'Offline Production Enclave';
  satisfy 'DMSR-9022' by 'Offline Production Enclave';
  satisfy 'DMSR-9439' by 'Offline Production Enclave';
  satisfy 'DMSR-3539' by 'Offline Production Enclave';
  satisfy 'DMSR-3332' by 'Offline Production Enclave';
  satisfy 'DMSR-2109' by 'Offline Production Enclave';
  satisfy 'DMSR-1632' by 'Offline Production Enclave';
  satisfy 'DMSR-4291' by 'Offline Production Enclave';
  satisfy 'DMSR-1602' by 'Offline Production Enclave';
  satisfy 'DMSR-1528' by 'Offline Production Enclave';
  satisfy 'DMSR-8994' by 'Offline Production Enclave';
  satisfy 'DMSR-1623' by 'Offline Production Enclave';
  satisfy 'DMSR-5586' by 'Offline Production Enclave';
  satisfy 'DMSR-9307' by 'Offline Production Enclave';
  satisfy 'EP-DM-CON-ICD-0037' by 'Offline Production Enclave';
  part def 'LSP Web API Def';
  part 'LSP Web API' : 'LSP Web API Def';
  satisfy 'DMSR-6585' by 'LSP Web API';
  satisfy 'DMSR-8325' by 'LSP Web API';
  satisfy 'DMSR-6475' by 'LSP Web API';
  satisfy 'DMSR-8494' by 'LSP Web API';
  satisfy 'DMSR-7847' by 'LSP Web API';
  satisfy 'DMSR-5135' by 'LSP Web API';
  satisfy 'DMSR-5909' by 'LSP Web API';
  satisfy 'DMSR-5792' by 'LSP Web API';
  satisfy 'DMSR-5457' by 'LSP Web API';
  satisfy 'DMSR-3770' by 'LSP Web API';
  satisfy 'DMSR-6987' by 'LSP Web API';
  satisfy 'DMSR-2551' by 'LSP Web API';
  satisfy 'DMSR-8958b' by 'LSP Web API';
  satisfy 'DMSR-1436' by 'LSP Web API';
  satisfy 'DMSR-1933' by 'LSP Web API';
  part def 'LSP Web API SW Def';
  part 'LSP Web API SW' : 'LSP Web API SW Def';
  satisfy 'DMSR-6585' by 'LSP Web API SW';
  satisfy 'DMSR-8325' by 'LSP Web API SW';
  satisfy 'DMSR-6475' by 'LSP Web API SW';
  satisfy 'DMSR-8494' by 'LSP Web API SW';
  satisfy 'DMSR-7847' by 'LSP Web API SW';
  satisfy 'DMSR-5135' by 'LSP Web API SW';
  satisfy 'DMSR-5909' by 'LSP Web API SW';
  satisfy 'DMSR-5792' by 'LSP Web API SW';
  satisfy 'DMSR-5457' by 'LSP Web API SW';
  satisfy 'DMSR-3770' by 'LSP Web API SW';
  satisfy 'DMSR-6987' by 'LSP Web API SW';
  satisfy 'DMSR-2551' by 'LSP Web API SW';
  satisfy 'DMSR-8958b' by 'LSP Web API SW';
  satisfy 'DMSR-1436' by 'LSP Web API SW';
  satisfy 'DMSR-1933' by 'LSP Web API SW';
  part def 'Image/Cutout Server Def';
  part 'Image/Cutout Server' : 'Image/Cutout Server Def';
  satisfy 'DMSR-6585' by 'Image/Cutout Server';
  satisfy 'DMSR-7847' by 'Image/Cutout Server';
  satisfy 'DMSR-5135' by 'Image/Cutout Server';
  satisfy 'DMSR-2551' by 'Image/Cutout Server';
  satisfy 'DMSR-8958b' by 'Image/Cutout Server';
  satisfy 'DMSR-1436' by 'Image/Cutout Server';
  satisfy 'DMSR-1933' by 'Image/Cutout Server';
  satisfy 'DMSR-2203' by 'Image/Cutout Server';
  satisfy 'DMSR-9748' by 'Image/Cutout Server';
  satisfy 'DMSR-4497' by 'Image/Cutout Server';
  satisfy 'DMSR-8173' by 'Image/Cutout Server';
  satisfy 'DMSR-1538' by 'Image/Cutout Server';
  satisfy 'EP-DM-CON-ICD-0034' by 'Image/Cutout Server';
  part def 'DBB Ingest/Metadata Management Def';
  part 'DBB Ingest/Metadata Management' : 'DBB Ingest/Metadata Management Def';
  satisfy 'DMSR-8525' by 'DBB Ingest/Metadata Management';
  satisfy 'DMSR-2005' by 'DBB Ingest/Metadata Management';
  satisfy 'DMSR-3617' by 'DBB Ingest/Metadata Management';
  satisfy 'DMSR-8494' by 'DBB Ingest/Metadata Management';
  satisfy 'DMSR-3337' by 'DBB Ingest/Metadata Management';
  satisfy 'DMSR-9599' by 'DBB Ingest/Metadata Management';
  satisfy 'DMSR-7847' by 'DBB Ingest/Metadata Management';
  satisfy 'DMSR-1963' by 'DBB Ingest/Metadata Management';
  satisfy 'DMSR-3004' by 'DBB Ingest/Metadata Management';
  satisfy 'DMSR-3997' by 'DBB Ingest/Metadata Management';
  satisfy 'DMSR-5909' by 'DBB Ingest/Metadata Management';
  satisfy 'DMSR-1570' by 'DBB Ingest/Metadata Management';
  satisfy 'DMSR-8254' by 'DBB Ingest/Metadata Management';
  satisfy 'DMSR-3565' by 'DBB Ingest/Metadata Management';
  satisfy 'DMSR-9563' by 'DBB Ingest/Metadata Management';
  satisfy 'DMSR-2551' by 'DBB Ingest/Metadata Management';
  satisfy 'DMSR-1436' by 'DBB Ingest/Metadata Management';
  satisfy 'DMSR-1933' by 'DBB Ingest/Metadata Management';
  satisfy 'OCS-DM-COM-ICD-0047' by 'DBB Ingest/Metadata Management';
  part def 'DBB Ingest/Metadata Management SW Def';
  part 'DBB Ingest/Metadata Management SW' : 'DBB Ingest/Metadata Management SW Def';
  satisfy 'DMSR-8525' by 'DBB Ingest/Metadata Management SW';
  satisfy 'DMSR-2005' by 'DBB Ingest/Metadata Management SW';
  satisfy 'DMSR-3617' by 'DBB Ingest/Metadata Management SW';
  satisfy 'DMSR-8494' by 'DBB Ingest/Metadata Management SW';
  satisfy 'DMSR-3337' by 'DBB Ingest/Metadata Management SW';
  satisfy 'DMSR-9599' by 'DBB Ingest/Metadata Management SW';
  satisfy 'DMSR-7847' by 'DBB Ingest/Metadata Management SW';
  satisfy 'DMSR-1963' by 'DBB Ingest/Metadata Management SW';
  satisfy 'DMSR-3004' by 'DBB Ingest/Metadata Management SW';
  satisfy 'DMSR-3997' by 'DBB Ingest/Metadata Management SW';
  satisfy 'DMSR-5909' by 'DBB Ingest/Metadata Management SW';
  satisfy 'DMSR-1570' by 'DBB Ingest/Metadata Management SW';
  satisfy 'DMSR-8254' by 'DBB Ingest/Metadata Management SW';
  satisfy 'DMSR-3565' by 'DBB Ingest/Metadata Management SW';
  satisfy 'DMSR-9563' by 'DBB Ingest/Metadata Management SW';
  satisfy 'DMSR-2551' by 'DBB Ingest/Metadata Management SW';
  satisfy 'DMSR-1436' by 'DBB Ingest/Metadata Management SW';
  satisfy 'DMSR-1933' by 'DBB Ingest/Metadata Management SW';
  satisfy 'OCS-DM-COM-ICD-0047' by 'DBB Ingest/Metadata Management SW';
  satisfy 'DMSR-4591' by 'DBB Ingest/Metadata Management SW';
  satisfy 'DMSR-3443' by 'DBB Ingest/Metadata Management SW';
  satisfy 'DMSR-4522' by 'DBB Ingest/Metadata Management SW';
  satisfy 'DMSR-1601' by 'DBB Ingest/Metadata Management SW';
  satisfy 'DMSR-3731' by 'DBB Ingest/Metadata Management SW';
  satisfy 'DMSR-6640' by 'DBB Ingest/Metadata Management SW';
  satisfy 'DMSR-6663' by 'DBB Ingest/Metadata Management SW';
  satisfy 'DMSR-8700' by 'DBB Ingest/Metadata Management SW';
  satisfy 'DMSR-8104' by 'DBB Ingest/Metadata Management SW';
  satisfy 'DMSR-3757' by 'DBB Ingest/Metadata Management SW';
  satisfy 'DMSR-3002' by 'DBB Ingest/Metadata Management SW';
  satisfy 'DMSR-3967' by 'DBB Ingest/Metadata Management SW';
  satisfy 'DMSR-7545' by 'DBB Ingest/Metadata Management SW';
  satisfy 'DMSR-3705' by 'DBB Ingest/Metadata Management SW';
  satisfy 'DMSR-9395' by 'DBB Ingest/Metadata Management SW';
  satisfy 'DMSR-1602' by 'DBB Ingest/Metadata Management SW';
  satisfy 'DMSR-9631' by 'DBB Ingest/Metadata Management SW';
  satisfy 'DMSR-8663' by 'DBB Ingest/Metadata Management SW';
  satisfy 'DMSR-2203' by 'DBB Ingest/Metadata Management SW';
  satisfy 'DMSR-5575' by 'DBB Ingest/Metadata Management SW';
  part def 'Distributed Database Def';
  part 'Distributed Database' : 'Distributed Database Def';
  satisfy 'DMSR-8325' by 'Distributed Database';
  satisfy 'DMSR-3617' by 'Distributed Database';
  satisfy 'DMSR-3770' by 'Distributed Database';
  satisfy 'DMSR-6987' by 'Distributed Database';
  satisfy 'DMSR-9580' by 'Distributed Database';
  satisfy 'DMSR-3612' by 'Distributed Database';
  satisfy 'DMSR-4054' by 'Distributed Database';
  satisfy 'DMSR-4012' by 'Distributed Database';
  satisfy 'DMSR-1060' by 'Distributed Database';
  satisfy 'DMSR-8973' by 'Distributed Database';
  satisfy 'DMSR-5264' by 'Distributed Database';
  satisfy 'DMSR-7938' by 'Distributed Database';
  satisfy 'DMSR-1083' by 'Distributed Database';
  satisfy 'DMSR-9631' by 'Distributed Database';
  satisfy 'DMSR-8663' by 'Distributed Database';
  satisfy 'DMSR-2203' by 'Distributed Database';
  satisfy 'DMSR-1851' by 'Distributed Database';
  satisfy 'DMSR-7695' by 'Distributed Database';
  satisfy 'DMSR-8595' by 'Distributed Database';
  satisfy 'DMSR-7328' by 'Distributed Database';
  satisfy 'DMSR-7791' by 'Distributed Database';
  satisfy 'DMSR-6131' by 'Distributed Database';
  satisfy 'DMSR-3710' by 'Distributed Database';
  satisfy 'DMSR-1961' by 'Distributed Database';
  satisfy 'DMSR-9570' by 'Distributed Database';
  satisfy 'DMSR-1538' by 'Distributed Database';
  satisfy 'DMSR-3608' by 'Distributed Database';
  satisfy 'DMSR-6487' by 'Distributed Database';
  satisfy 'DMSR-3743' by 'Distributed Database';
  part def 'ADQL Translator Def';
  part 'ADQL Translator' : 'ADQL Translator Def';
  satisfy 'DMSR-8325' by 'ADQL Translator';
  satisfy 'DMSR-6475' by 'ADQL Translator';
  satisfy 'DMSR-5135' by 'ADQL Translator';
  satisfy 'DMSR-3770' by 'ADQL Translator';
  satisfy 'DMSR-3612' by 'ADQL Translator';
  satisfy 'DMSR-3731' by 'ADQL Translator';
  satisfy 'DMSR-9631' by 'ADQL Translator';
  satisfy 'DMSR-9748' by 'ADQL Translator';
  satisfy 'DMSR-7695' by 'ADQL Translator';
  satisfy 'DMSR-1376' by 'ADQL Translator';
  satisfy 'DMSR-8595' by 'ADQL Translator';
  satisfy 'DMSR-2053' by 'ADQL Translator';
  satisfy 'DMSR-1538' by 'ADQL Translator';
  satisfy 'DMSR-3608' by 'ADQL Translator';
  satisfy 'EP-DM-CON-ICD-0034' by 'ADQL Translator';
  part def 'DAC Chile Enclave Def';
  part 'DAC Chile Enclave' : 'DAC Chile Enclave Def';
  satisfy 'DMSR-8325' by 'DAC Chile Enclave';
  satisfy 'DMSR-3617' by 'DAC Chile Enclave';
  satisfy 'DMSR-6475' by 'DAC Chile Enclave';
  satisfy 'DMSR-8494' by 'DAC Chile Enclave';
  satisfy 'DMSR-3337' by 'DAC Chile Enclave';
  satisfy 'DMSR-7847' by 'DAC Chile Enclave';
  satisfy 'DMSR-3004' by 'DAC Chile Enclave';
  satisfy 'DMSR-5909' by 'DAC Chile Enclave';
  satisfy 'DMSR-1570' by 'DAC Chile Enclave';
  satisfy 'DMSR-8254' by 'DAC Chile Enclave';
  satisfy 'DMSR-5792' by 'DAC Chile Enclave';
  satisfy 'DMSR-5457' by 'DAC Chile Enclave';
  satisfy 'DMSR-6515' by 'DAC Chile Enclave';
  satisfy 'DMSR-2551' by 'DAC Chile Enclave';
  satisfy 'DMSR-8958b' by 'DAC Chile Enclave';
  satisfy 'DMSR-1436' by 'DAC Chile Enclave';
  satisfy 'DMSR-1933' by 'DAC Chile Enclave';
  satisfy 'DMSR-3612' by 'DAC Chile Enclave';
  satisfy 'DMSR-9308' by 'DAC Chile Enclave';
  satisfy 'OCS-DM-COM-ICD-0029' by 'DAC Chile Enclave';
  part def 'DAC US Enclave Def';
  part 'DAC US Enclave' : 'DAC US Enclave Def';
  satisfy 'DMSR-8325' by 'DAC US Enclave';
  satisfy 'DMSR-3617' by 'DAC US Enclave';
  satisfy 'DMSR-6475' by 'DAC US Enclave';
  satisfy 'DMSR-8494' by 'DAC US Enclave';
  satisfy 'DMSR-3337' by 'DAC US Enclave';
  satisfy 'DMSR-7847' by 'DAC US Enclave';
  satisfy 'DMSR-3004' by 'DAC US Enclave';
  satisfy 'DMSR-5909' by 'DAC US Enclave';
  satisfy 'DMSR-1570' by 'DAC US Enclave';
  satisfy 'DMSR-3565' by 'DAC US Enclave';
  satisfy 'DMSR-9563' by 'DAC US Enclave';
  satisfy 'DMSR-5792' by 'DAC US Enclave';
  satisfy 'DMSR-5457' by 'DAC US Enclave';
  satisfy 'DMSR-6515' by 'DAC US Enclave';
  satisfy 'DMSR-2551' by 'DAC US Enclave';
  satisfy 'DMSR-8958b' by 'DAC US Enclave';
  satisfy 'DMSR-1436' by 'DAC US Enclave';
  satisfy 'DMSR-1933' by 'DAC US Enclave';
  satisfy 'DMSR-3612' by 'DAC US Enclave';
  satisfy 'DMSR-9308' by 'DAC US Enclave';
  satisfy 'OCS-DM-COM-ICD-0029' by 'DAC US Enclave';
  satisfy 'DMSR-7456' by 'DAC US Enclave';
  satisfy 'DMSR-3443' by 'DAC US Enclave';
  satisfy 'DMSR-3919' by 'DAC US Enclave';
  satisfy 'DMSR-4522' by 'DAC US Enclave';
  satisfy 'DMSR-9625' by 'DAC US Enclave';
  satisfy 'DMSR-3731' by 'DAC US Enclave';
  satisfy 'DMSR-6640' by 'DAC US Enclave';
  satisfy 'DMSR-3757' by 'DAC US Enclave';
  satisfy 'DMSR-1632' by 'DAC US Enclave';
  satisfy 'DMSR-1602' by 'DAC US Enclave';
  satisfy 'DMSR-9631' by 'DAC US Enclave';
  satisfy 'DMSR-1155' by 'DAC US Enclave';
  satisfy 'DMSR-3973' by 'DAC US Enclave';
  satisfy 'DMSR-4497' by 'DAC US Enclave';
  satisfy 'DMSR-3406' by 'DAC US Enclave';
  satisfy 'DMSR-1851' by 'DAC US Enclave';
  satisfy 'DMSR-8994' by 'DAC US Enclave';
  satisfy 'DMSR-1623' by 'DAC US Enclave';
  satisfy 'DMSR-7695' by 'DAC US Enclave';
  satisfy 'DMSR-1376' by 'DAC US Enclave';
  satisfy 'DMSR-5600' by 'DAC US Enclave';
  satisfy 'DMSR-3446' by 'DAC US Enclave';
  satisfy 'DMSR-8595' by 'DAC US Enclave';
  satisfy 'DMSR-6131' by 'DAC US Enclave';
  satisfy 'DMSR-2053' by 'DAC US Enclave';
  satisfy 'DMSR-3710' by 'DAC US Enclave';
  satisfy 'DMSR-1961' by 'DAC US Enclave';
  satisfy 'DMSR-9570' by 'DAC US Enclave';
  part def 'DBB Storage Def';
  part 'DBB Storage' : 'DBB Storage Def';
  satisfy 'DMSR-3617' by 'DBB Storage';
  satisfy 'DMSR-8494' by 'DBB Storage';
  satisfy 'DMSR-3337' by 'DBB Storage';
  satisfy 'DMSR-9599' by 'DBB Storage';
  satisfy 'DMSR-7847' by 'DBB Storage';
  satisfy 'DMSR-1963' by 'DBB Storage';
  satisfy 'DMSR-3004' by 'DBB Storage';
  satisfy 'DMSR-5909' by 'DBB Storage';
  satisfy 'DMSR-1570' by 'DBB Storage';
  satisfy 'DMSR-3565' by 'DBB Storage';
  satisfy 'DMSR-9563' by 'DBB Storage';
  satisfy 'DMSR-2551' by 'DBB Storage';
  satisfy 'DMSR-1436' by 'DBB Storage';
  part def 'DBB Transport/Replication/Backup Def';
  part 'DBB Transport/Replication/Backup' : 'DBB Transport/Replication/Backup Def';
  satisfy 'DMSR-8494' by 'DBB Transport/Replication/Backup';
  satisfy 'DMSR-9599' by 'DBB Transport/Replication/Backup';
  satisfy 'DMSR-7847' by 'DBB Transport/Replication/Backup';
  satisfy 'DMSR-3004' by 'DBB Transport/Replication/Backup';
  satisfy 'DMSR-5909' by 'DBB Transport/Replication/Backup';
  satisfy 'DMSR-1570' by 'DBB Transport/Replication/Backup';
  satisfy 'DMSR-3565' by 'DBB Transport/Replication/Backup';
  satisfy 'DMSR-9563' by 'DBB Transport/Replication/Backup';
  satisfy 'DMSR-4591' by 'DBB Transport/Replication/Backup';
  satisfy 'DMSR-3443' by 'DBB Transport/Replication/Backup';
  satisfy 'DMSR-1601' by 'DBB Transport/Replication/Backup';
  satisfy 'DMSR-3731' by 'DBB Transport/Replication/Backup';
  satisfy 'DMSR-6640' by 'DBB Transport/Replication/Backup';
  satisfy 'DMSR-6663' by 'DBB Transport/Replication/Backup';
  satisfy 'DMSR-8700' by 'DBB Transport/Replication/Backup';
  satisfy 'DMSR-8104' by 'DBB Transport/Replication/Backup';
  satisfy 'DMSR-3757' by 'DBB Transport/Replication/Backup';
  satisfy 'DMSR-3002' by 'DBB Transport/Replication/Backup';
  satisfy 'DMSR-1602' by 'DBB Transport/Replication/Backup';
  satisfy 'DMSR-1155' by 'DBB Transport/Replication/Backup';
  satisfy 'DMSR-1851' by 'DBB Transport/Replication/Backup';
  satisfy 'DMSR-8994' by 'DBB Transport/Replication/Backup';
  satisfy 'DMSR-1623' by 'DBB Transport/Replication/Backup';
  satisfy 'DMSR-3446' by 'DBB Transport/Replication/Backup';
  satisfy 'DMSR-1961' by 'DBB Transport/Replication/Backup';
  satisfy 'DMSR-6487' by 'DBB Transport/Replication/Backup';
  part def 'DBB Transport/Replication/Backup SW Def';
  part 'DBB Transport/Replication/Backup SW' : 'DBB Transport/Replication/Backup SW Def';
  satisfy 'DMSR-8494' by 'DBB Transport/Replication/Backup SW';
  satisfy 'DMSR-9599' by 'DBB Transport/Replication/Backup SW';
  satisfy 'DMSR-7847' by 'DBB Transport/Replication/Backup SW';
  satisfy 'DMSR-3004' by 'DBB Transport/Replication/Backup SW';
  satisfy 'DMSR-5909' by 'DBB Transport/Replication/Backup SW';
  satisfy 'DMSR-1570' by 'DBB Transport/Replication/Backup SW';
  satisfy 'DMSR-3565' by 'DBB Transport/Replication/Backup SW';
  satisfy 'DMSR-9563' by 'DBB Transport/Replication/Backup SW';
  satisfy 'DMSR-4591' by 'DBB Transport/Replication/Backup SW';
  satisfy 'DMSR-3443' by 'DBB Transport/Replication/Backup SW';
  satisfy 'DMSR-1601' by 'DBB Transport/Replication/Backup SW';
  satisfy 'DMSR-3731' by 'DBB Transport/Replication/Backup SW';
  satisfy 'DMSR-6640' by 'DBB Transport/Replication/Backup SW';
  satisfy 'DMSR-6663' by 'DBB Transport/Replication/Backup SW';
  satisfy 'DMSR-8700' by 'DBB Transport/Replication/Backup SW';
  satisfy 'DMSR-8104' by 'DBB Transport/Replication/Backup SW';
  satisfy 'DMSR-3757' by 'DBB Transport/Replication/Backup SW';
  satisfy 'DMSR-3002' by 'DBB Transport/Replication/Backup SW';
  satisfy 'DMSR-1602' by 'DBB Transport/Replication/Backup SW';
  satisfy 'DMSR-1155' by 'DBB Transport/Replication/Backup SW';
  satisfy 'DMSR-1851' by 'DBB Transport/Replication/Backup SW';
  satisfy 'DMSR-8994' by 'DBB Transport/Replication/Backup SW';
  satisfy 'DMSR-1623' by 'DBB Transport/Replication/Backup SW';
  satisfy 'DMSR-3446' by 'DBB Transport/Replication/Backup SW';
  satisfy 'DMSR-1961' by 'DBB Transport/Replication/Backup SW';
  satisfy 'DMSR-6487' by 'DBB Transport/Replication/Backup SW';
  part def 'MOPS and Forced Photometry Def';
  part 'MOPS and Forced Photometry' : 'MOPS and Forced Photometry Def';
  satisfy 'DMSR-8494' by 'MOPS and Forced Photometry';
  satisfy 'DMSR-9308' by 'MOPS and Forced Photometry';
  satisfy 'DMSR-7456' by 'MOPS and Forced Photometry';
  satisfy 'DMSR-9395' by 'MOPS and Forced Photometry';
  satisfy 'DMSR-4291' by 'MOPS and Forced Photometry';
  satisfy 'DMSR-1602' by 'MOPS and Forced Photometry';
  satisfy 'DMSR-7420' by 'MOPS and Forced Photometry';
  satisfy 'DMSR-8956' by 'MOPS and Forced Photometry';
  satisfy 'DMSR-3852' by 'MOPS and Forced Photometry';
  satisfy 'DMSR-8758' by 'MOPS and Forced Photometry';
  satisfy 'DMSR-7446' by 'MOPS and Forced Photometry';
  satisfy 'DMSR-3446' by 'MOPS and Forced Photometry';
  part def 'Bulk Distribution Def';
  part 'Bulk Distribution' : 'Bulk Distribution Def';
  satisfy 'DMSR-9599' by 'Bulk Distribution';
  satisfy 'DMSR-7847' by 'Bulk Distribution';
  satisfy 'DMSR-3565' by 'Bulk Distribution';
  satisfy 'DMSR-9563' by 'Bulk Distribution';
  satisfy 'DMSR-5792' by 'Bulk Distribution';
  satisfy 'DMSR-1601' by 'Bulk Distribution';
  satisfy 'DMSR-3731' by 'Bulk Distribution';
  satisfy 'DMSR-3011' by 'Bulk Distribution';
  satisfy 'DMSR-8994' by 'Bulk Distribution';
  satisfy 'DMSR-1623' by 'Bulk Distribution';
  satisfy 'DMSR-8173' by 'Bulk Distribution';
  satisfy 'EP-DM-CON-ICD-0004' by 'Bulk Distribution';
  satisfy 'EP-DM-CON-ICD-0009' by 'Bulk Distribution';
  satisfy 'EP-DM-CON-ICD-0019' by 'Bulk Distribution';
  satisfy 'EP-DM-CON-ICD-0021' by 'Bulk Distribution';
  part def 'LSP Portal Def';
  part 'LSP Portal' : 'LSP Portal Def';
  satisfy 'DMSR-7847' by 'LSP Portal';
  satisfy 'DMSR-1236' by 'LSP Portal';
  satisfy 'DMSR-5909' by 'LSP Portal';
  satisfy 'DMSR-5792' by 'LSP Portal';
  satisfy 'DMSR-5457' by 'LSP Portal';
  satisfy 'DMSR-9308' by 'LSP Portal';
  satisfy 'DMSR-3919' by 'LSP Portal';
  satisfy 'DMSR-3731' by 'LSP Portal';
  satisfy 'DMSR-5731' by 'LSP Portal';
  satisfy 'DMSR-3002' by 'LSP Portal';
  satisfy 'DMSR-8994' by 'LSP Portal';
  satisfy 'DMSR-1623' by 'LSP Portal';
  satisfy 'DMSR-6131' by 'LSP Portal';
  satisfy 'DMSR-2053' by 'LSP Portal';
  satisfy 'DMSR-3710' by 'LSP Portal';
  satisfy 'DMSR-1961' by 'LSP Portal';
  satisfy 'DMSR-9570' by 'LSP Portal';
  satisfy 'DMSR-1538' by 'LSP Portal';
  satisfy 'DMSR-3608' by 'LSP Portal';
  satisfy 'DMSR-6487' by 'LSP Portal';
  satisfy 'DMSR-3743' by 'LSP Portal';
  satisfy 'DMSR-3451' by 'LSP Portal';
  satisfy 'DMSR-9495' by 'LSP Portal';
  part def 'LSP JupyterLab Def';
  part 'LSP JupyterLab' : 'LSP JupyterLab Def';
  satisfy 'DMSR-7847' by 'LSP JupyterLab';
  satisfy 'DMSR-5909' by 'LSP JupyterLab';
  satisfy 'DMSR-5792' by 'LSP JupyterLab';
  satisfy 'DMSR-5457' by 'LSP JupyterLab';
  satisfy 'DMSR-3919' by 'LSP JupyterLab';
  satisfy 'DMSR-3731' by 'LSP JupyterLab';
  satisfy 'DMSR-5731' by 'LSP JupyterLab';
  satisfy 'DMSR-3002' by 'LSP JupyterLab';
  satisfy 'DMSR-8994' by 'LSP JupyterLab';
  satisfy 'DMSR-1623' by 'LSP JupyterLab';
  part def 'SUIT Def';
  part 'SUIT' : 'SUIT Def';
  satisfy 'DMSR-7847' by 'SUIT';
  satisfy 'DMSR-1236' by 'SUIT';
  satisfy 'DMSR-5909' by 'SUIT';
  satisfy 'DMSR-5792' by 'SUIT';
  satisfy 'DMSR-5457' by 'SUIT';
  satisfy 'DMSR-9308' by 'SUIT';
  satisfy 'DMSR-3919' by 'SUIT';
  satisfy 'DMSR-3731' by 'SUIT';
  satisfy 'DMSR-5731' by 'SUIT';
  satisfy 'DMSR-3002' by 'SUIT';
  satisfy 'DMSR-8994' by 'SUIT';
  satisfy 'DMSR-1623' by 'SUIT';
  satisfy 'DMSR-6131' by 'SUIT';
  satisfy 'DMSR-2053' by 'SUIT';
  satisfy 'DMSR-3710' by 'SUIT';
  satisfy 'DMSR-1961' by 'SUIT';
  satisfy 'DMSR-9570' by 'SUIT';
  satisfy 'DMSR-1538' by 'SUIT';
  satisfy 'DMSR-3608' by 'SUIT';
  satisfy 'DMSR-6487' by 'SUIT';
  satisfy 'DMSR-3743' by 'SUIT';
  satisfy 'DMSR-3451' by 'SUIT';
  part def 'LSP JupyterLab SW Def';
  part 'LSP JupyterLab SW' : 'LSP JupyterLab SW Def';
  satisfy 'DMSR-7847' by 'LSP JupyterLab SW';
  satisfy 'DMSR-5909' by 'LSP JupyterLab SW';
  satisfy 'DMSR-5792' by 'LSP JupyterLab SW';
  satisfy 'DMSR-5457' by 'LSP JupyterLab SW';
  satisfy 'DMSR-3919' by 'LSP JupyterLab SW';
  satisfy 'DMSR-3731' by 'LSP JupyterLab SW';
  satisfy 'DMSR-5731' by 'LSP JupyterLab SW';
  satisfy 'DMSR-3002' by 'LSP JupyterLab SW';
  satisfy 'DMSR-8994' by 'LSP JupyterLab SW';
  satisfy 'DMSR-1623' by 'LSP JupyterLab SW';
  part def 'Data Butler Def';
  part 'Data Butler' : 'Data Butler Def';
  satisfy 'DMSR-6570' by 'Data Butler';
  satisfy 'DMSR-9625' by 'Data Butler';
  satisfy 'DMSR-7450' by 'Data Butler';
  satisfy 'DMSR-2203' by 'Data Butler';
  satisfy 'DMSR-8804' by 'Data Butler';
  satisfy 'DMSR-9725' by 'Data Butler';
  satisfy 'DMSR-8956' by 'Data Butler';
  satisfy 'DMSR-8994' by 'Data Butler';
  satisfy 'EP-DM-CON-ICD-0035' by 'Data Butler';
  part def 'Task Framework Def';
  part 'Task Framework' : 'Task Framework Def';
  satisfy 'DMSR-6570' by 'Task Framework';
  satisfy 'DMSR-6300' by 'Task Framework';
  part def 'OCS-Driven Batch Def';
  part 'OCS-Driven Batch' : 'OCS-Driven Batch Def';
  satisfy 'DMSR-3004' by 'OCS-Driven Batch';
  satisfy 'OCS-DM-COM-ICD-0013' by 'OCS-Driven Batch';
  satisfy 'OCS-DM-COM-ICD-0014' by 'OCS-Driven Batch';
  satisfy 'OCS-DM-COM-ICD-0015' by 'OCS-Driven Batch';
  satisfy 'OCS-DM-COM-ICD-0035' by 'OCS-Driven Batch';
  satisfy 'OCS-DM-COM-ICD-0036' by 'OCS-Driven Batch';
  satisfy 'OCS-DM-COM-ICD-0037' by 'OCS-Driven Batch';
  satisfy 'OCS-DM-COM-ICD-0038' by 'OCS-Driven Batch';
  satisfy 'OCS-DM-COM-ICD-0039' by 'OCS-Driven Batch';
  satisfy 'OCS-DM-COM-ICD-0040' by 'OCS-Driven Batch';
  satisfy 'DMSR-4591' by 'OCS-Driven Batch';
  satisfy 'DMSR-9791' by 'OCS-Driven Batch';
  satisfy 'DMSR-6640' by 'OCS-Driven Batch';
  satisfy 'DMSR-8717' by 'OCS-Driven Batch';
  satisfy 'DMSR-1528' by 'OCS-Driven Batch';
  satisfy 'DMSR-3410' by 'OCS-Driven Batch';
  satisfy 'DMSR-9849' by 'OCS-Driven Batch';
  satisfy 'DMSR-8994' by 'OCS-Driven Batch';
  satisfy 'DMSR-7327' by 'OCS-Driven Batch';
  satisfy 'DMSR-1623' by 'OCS-Driven Batch';
  satisfy 'OCS-DM-COM-ICD-0003' by 'OCS-Driven Batch';
  satisfy 'OCS-DM-COM-ICD-0009' by 'OCS-Driven Batch';
  satisfy 'OCS-DM-COM-ICD-0012' by 'OCS-Driven Batch';
  part def 'OCS Batch SW Def';
  part 'OCS Batch SW' : 'OCS Batch SW Def';
  satisfy 'DMSR-3004' by 'OCS Batch SW';
  satisfy 'OCS-DM-COM-ICD-0013' by 'OCS Batch SW';
  satisfy 'OCS-DM-COM-ICD-0014' by 'OCS Batch SW';
  satisfy 'OCS-DM-COM-ICD-0015' by 'OCS Batch SW';
  satisfy 'OCS-DM-COM-ICD-0035' by 'OCS Batch SW';
  satisfy 'OCS-DM-COM-ICD-0036' by 'OCS Batch SW';
  satisfy 'OCS-DM-COM-ICD-0037' by 'OCS Batch SW';
  satisfy 'OCS-DM-COM-ICD-0038' by 'OCS Batch SW';
  satisfy 'OCS-DM-COM-ICD-0039' by 'OCS Batch SW';
  satisfy 'OCS-DM-COM-ICD-0040' by 'OCS Batch SW';
  satisfy 'DMSR-4591' by 'OCS Batch SW';
  satisfy 'DMSR-9791' by 'OCS Batch SW';
  satisfy 'DMSR-6640' by 'OCS Batch SW';
  satisfy 'DMSR-8717' by 'OCS Batch SW';
  satisfy 'DMSR-1528' by 'OCS Batch SW';
  satisfy 'DMSR-3410' by 'OCS Batch SW';
  satisfy 'DMSR-9849' by 'OCS Batch SW';
  satisfy 'DMSR-8994' by 'OCS Batch SW';
  satisfy 'DMSR-7327' by 'OCS Batch SW';
  satisfy 'DMSR-1623' by 'OCS Batch SW';
  satisfy 'OCS-DM-COM-ICD-0003' by 'OCS Batch SW';
  satisfy 'OCS-DM-COM-ICD-0009' by 'OCS Batch SW';
  satisfy 'OCS-DM-COM-ICD-0012' by 'OCS Batch SW';
  part def 'Calibration SW Def';
  part 'Calibration SW' : 'Calibration SW Def';
  satisfy 'DMSR-3004' by 'Calibration SW';
  satisfy 'DMSR-9791' by 'Calibration SW';
  satisfy 'DMSR-8717' by 'Calibration SW';
  satisfy 'DMSR-8956' by 'Calibration SW';
  part def 'Batch Production Def';
  part 'Batch Production' : 'Batch Production Def';
  satisfy 'DMSR-5970' by 'Batch Production';
  satisfy 'DMSR-1570' by 'Batch Production';
  satisfy 'DMSR-4591' by 'Batch Production';
  satisfy 'DMSR-6663' by 'Batch Production';
  satisfy 'DMSR-3410' by 'Batch Production';
  satisfy 'DMSR-2825' by 'Batch Production';
  satisfy 'DMSR-7271' by 'Batch Production';
  satisfy 'DMSR-4721' by 'Batch Production';
  satisfy 'DMSR-6092' by 'Batch Production';
  satisfy 'DMSR-8956' by 'Batch Production';
  satisfy 'DMSR-8994' by 'Batch Production';
  satisfy 'DMSR-1623' by 'Batch Production';
  satisfy 'DMSR-6377' by 'Batch Production';
  satisfy 'DMSR-7560' by 'Batch Production';
  satisfy 'DMSR-6108' by 'Batch Production';
  part def 'Campaign Management Def';
  part 'Campaign Management' : 'Campaign Management Def';
  satisfy 'DMSR-5970' by 'Campaign Management';
  satisfy 'DMSR-1570' by 'Campaign Management';
  satisfy 'DMSR-4591' by 'Campaign Management';
  satisfy 'DMSR-6663' by 'Campaign Management';
  satisfy 'DMSR-3410' by 'Campaign Management';
  satisfy 'DMSR-2825' by 'Campaign Management';
  satisfy 'DMSR-7271' by 'Campaign Management';
  satisfy 'DMSR-4721' by 'Campaign Management';
  satisfy 'DMSR-8994' by 'Campaign Management';
  satisfy 'DMSR-1623' by 'Campaign Management';
  part def 'Workload/Workflow Management Def';
  part 'Workload/Workflow Management' : 'Workload/Workflow Management Def';
  satisfy 'DMSR-5970' by 'Workload/Workflow Management';
  satisfy 'DMSR-1570' by 'Workload/Workflow Management';
  satisfy 'DMSR-4591' by 'Workload/Workflow Management';
  satisfy 'DMSR-6663' by 'Workload/Workflow Management';
  satisfy 'DMSR-3410' by 'Workload/Workflow Management';
  satisfy 'DMSR-2825' by 'Workload/Workflow Management';
  satisfy 'DMSR-7271' by 'Workload/Workflow Management';
  satisfy 'DMSR-4721' by 'Workload/Workflow Management';
  satisfy 'DMSR-8956' by 'Workload/Workflow Management';
  satisfy 'DMSR-8994' by 'Workload/Workflow Management';
  satisfy 'DMSR-1623' by 'Workload/Workflow Management';
  satisfy 'DMSR-6519a' by 'Workload/Workflow Management';
  satisfy 'DMSR-6377' by 'Workload/Workflow Management';
  satisfy 'DMSR-7560' by 'Workload/Workflow Management';
  satisfy 'DMSR-6108' by 'Workload/Workflow Management';
  part def 'Base Facility Def';
  part 'Base Facility' : 'Base Facility Def';
  satisfy 'DMSR-5909' by 'Base Facility';
  satisfy 'DMSR-1570' by 'Base Facility';
  satisfy 'DMSR-6873' by 'Base Facility';
  satisfy 'DMSR-8254' by 'Base Facility';
  satisfy 'DMSR-9289' by 'Base Facility';
  satisfy 'DMSR-5792' by 'Base Facility';
  satisfy 'DMSR-6515' by 'Base Facility';
  satisfy 'OCS-DM-COM-ICD-0027' by 'Base Facility';
  satisfy 'DM-TS-CON-ICD-0003' by 'Base Facility';
  satisfy 'DMSR-4591' by 'Base Facility';
  satisfy 'DMSR-6640' by 'Base Facility';
  satisfy 'DMSR-6663' by 'Base Facility';
  satisfy 'DMSR-8700' by 'Base Facility';
  satisfy 'DMSR-8104' by 'Base Facility';
  satisfy 'DMSR-3757' by 'Base Facility';
  satisfy 'DMSR-6799' by 'Base Facility';
  satisfy 'DMSR-8994' by 'Base Facility';
  satisfy 'DMSR-7327' by 'Base Facility';
  satisfy 'DMSR-6933' by 'Base Facility';
  satisfy 'DMSR-1623' by 'Base Facility';
  satisfy 'DMSR-7823' by 'Base Facility';
  part def 'NCSA Facility Def';
  part 'NCSA Facility' : 'NCSA Facility Def';
  satisfy 'DMSR-5909' by 'NCSA Facility';
  satisfy 'DMSR-1570' by 'NCSA Facility';
  satisfy 'DMSR-6873' by 'NCSA Facility';
  satisfy 'DMSR-3565' by 'NCSA Facility';
  satisfy 'DMSR-9563' by 'NCSA Facility';
  satisfy 'DMSR-2324' by 'NCSA Facility';
  satisfy 'DMSR-5792' by 'NCSA Facility';
  satisfy 'DMSR-6515' by 'NCSA Facility';
  satisfy 'OCS-DM-COM-ICD-0027' by 'NCSA Facility';
  satisfy 'DM-TS-CON-ICD-0003' by 'NCSA Facility';
  satisfy 'DMSR-4591' by 'NCSA Facility';
  satisfy 'DMSR-6640' by 'NCSA Facility';
  satisfy 'DMSR-6663' by 'NCSA Facility';
  satisfy 'DMSR-8700' by 'NCSA Facility';
  satisfy 'DMSR-8104' by 'NCSA Facility';
  satisfy 'DMSR-3757' by 'NCSA Facility';
  satisfy 'DMSR-6799' by 'NCSA Facility';
  satisfy 'DMSR-8994' by 'NCSA Facility';
  satisfy 'DMSR-1623' by 'NCSA Facility';
  part def 'Commissioning Cluster Enclave Def';
  part 'Commissioning Cluster Enclave' : 'Commissioning Cluster Enclave Def';
  satisfy 'DMSR-5909' by 'Commissioning Cluster Enclave';
  satisfy 'DMSR-1570' by 'Commissioning Cluster Enclave';
  satisfy 'DMSR-8254' by 'Commissioning Cluster Enclave';
  satisfy 'DMSR-3757' by 'Commissioning Cluster Enclave';
  satisfy 'DMSR-8994' by 'Commissioning Cluster Enclave';
  satisfy 'DMSR-6933' by 'Commissioning Cluster Enclave';
  satisfy 'DMSR-1623' by 'Commissioning Cluster Enclave';
  part def 'Observatory Operations Data Def';
  part 'Observatory Operations Data' : 'Observatory Operations Data Def';
  satisfy 'DMSR-1570' by 'Observatory Operations Data';
  satisfy 'CA-DM-DAQ-ICD-0052' by 'Observatory Operations Data';
  satisfy 'DM-TS-CON-ICD-0003' by 'Observatory Operations Data';
  satisfy 'DM-TS-CON-ICD-0009' by 'Observatory Operations Data';
  satisfy 'DMSR-8994' by 'Observatory Operations Data';
  satisfy 'DMSR-1623' by 'Observatory Operations Data';
  satisfy 'DMSR-8173' by 'Observatory Operations Data';
  part def 'EFD Transformation Def';
  part 'EFD Transformation' : 'EFD Transformation Def';
  satisfy 'DMSR-1570' by 'EFD Transformation';
  satisfy 'OCS-DM-COM-ICD-0025' by 'EFD Transformation';
  satisfy 'OCS-DM-COM-ICD-0026' by 'EFD Transformation';
  satisfy 'OCS-DM-COM-ICD-0027' by 'EFD Transformation';
  satisfy 'OCS-DM-COM-ICD-0028' by 'EFD Transformation';
  satisfy 'OCS-DM-COM-ICD-0029' by 'EFD Transformation';
  satisfy 'OCS-DM-COM-ICD-0030' by 'EFD Transformation';
  satisfy 'DMSR-7456' by 'EFD Transformation';
  satisfy 'DMSR-4591' by 'EFD Transformation';
  satisfy 'DMSR-3443' by 'EFD Transformation';
  satisfy 'DMSR-8104' by 'EFD Transformation';
  satisfy 'DMSR-1155' by 'EFD Transformation';
  satisfy 'DMSR-8994' by 'EFD Transformation';
  satisfy 'DMSR-7327' by 'EFD Transformation';
  satisfy 'DMSR-1623' by 'EFD Transformation';
  satisfy 'DMSR-8173' by 'EFD Transformation';
  satisfy 'OCS-DM-COM-ICD-0003' by 'EFD Transformation';
  satisfy 'OCS-DM-COM-ICD-0004' by 'EFD Transformation';
  satisfy 'OCS-DM-COM-ICD-0008' by 'EFD Transformation';
  part def 'Observatory Operations Data Service SW Def';
  part 'Observatory Operations Data Service SW' : 'Observatory Operations Data Service SW Def';
  satisfy 'DMSR-1570' by 'Observatory Operations Data Service SW';
  satisfy 'CA-DM-DAQ-ICD-0052' by 'Observatory Operations Data Service SW';
  satisfy 'DM-TS-CON-ICD-0003' by 'Observatory Operations Data Service SW';
  satisfy 'DMSR-8994' by 'Observatory Operations Data Service SW';
  satisfy 'DMSR-1623' by 'Observatory Operations Data Service SW';
  satisfy 'DMSR-8173' by 'Observatory Operations Data Service SW';
  part def 'Summit to Base Network Def';
  part 'Summit to Base Network' : 'Summit to Base Network Def';
  satisfy 'DMSR-1570' by 'Summit to Base Network';
  satisfy 'DMSR-7309' by 'Summit to Base Network';
  satisfy 'DMSR-4221' by 'Summit to Base Network';
  satisfy 'DMSR-9952' by 'Summit to Base Network';
  satisfy 'DMSR-9915' by 'Summit to Base Network';
  satisfy 'DMSR-8151' by 'Summit to Base Network';
  satisfy 'DMSR-3053' by 'Summit to Base Network';
  satisfy 'OCS-DM-COM-ICD-0053' by 'Summit to Base Network';
  satisfy 'DMSR-8104' by 'Summit to Base Network';
  satisfy 'DMSR-3757' by 'Summit to Base Network';
  part def 'Base to Archive Network Def';
  part 'Base to Archive Network' : 'Base to Archive Network Def';
  satisfy 'DMSR-1570' by 'Base to Archive Network';
  satisfy 'DMSR-9487' by 'Base to Archive Network';
  satisfy 'DMSR-9351' by 'Base to Archive Network';
  satisfy 'DMSR-9504' by 'Base to Archive Network';
  satisfy 'DMSR-1578' by 'Base to Archive Network';
  satisfy 'DMSR-8893' by 'Base to Archive Network';
  satisfy 'DMSR-9422' by 'Base to Archive Network';
  satisfy 'DMSR-3721' by 'Base to Archive Network';
  satisfy 'DMSR-2127' by 'Base to Archive Network';
  satisfy 'OCS-DM-COM-ICD-0054' by 'Base to Archive Network';
  satisfy 'DMSR-8104' by 'Base to Archive Network';
  satisfy 'DMSR-3757' by 'Base to Archive Network';
  part def 'Base LAN Network Def';
  part 'Base LAN Network' : 'Base LAN Network Def';
  satisfy 'DMSR-1570' by 'Base LAN Network';
  satisfy 'DMSR-5792' by 'Base LAN Network';
  satisfy 'DMSR-5457' by 'Base LAN Network';
  satisfy 'DMSR-8104' by 'Base LAN Network';
  satisfy 'DMSR-3757' by 'Base LAN Network';
  satisfy 'DMSR-7823' by 'Base LAN Network';
  part def 'NCSA LAN Network Def';
  part 'NCSA LAN Network' : 'NCSA LAN Network Def';
  satisfy 'DMSR-1570' by 'NCSA LAN Network';
  satisfy 'DMSR-8893' by 'NCSA LAN Network';
  satisfy 'DMSR-9422' by 'NCSA LAN Network';
  satisfy 'DMSR-3721' by 'NCSA LAN Network';
  satisfy 'DMSR-2127' by 'NCSA LAN Network';
  satisfy 'DMSR-5792' by 'NCSA LAN Network';
  satisfy 'DMSR-5457' by 'NCSA LAN Network';
  part def 'Network Management Def';
  part 'Network Management' : 'Network Management Def';
  satisfy 'DMSR-1570' by 'Network Management';
  satisfy 'DMSR-3053' by 'Network Management';
  satisfy 'DMSR-4591' by 'Network Management';
  satisfy 'DMSR-3757' by 'Network Management';
  part def 'DBB Lifetime Management Def';
  part 'DBB Lifetime Management' : 'DBB Lifetime Management Def';
  satisfy 'DMSR-2551' by 'DBB Lifetime Management';
  satisfy 'DMSR-1436' by 'DBB Lifetime Management';
  satisfy 'DMSR-1933' by 'DBB Lifetime Management';
  satisfy 'DMSR-3973' by 'DBB Lifetime Management';
  satisfy 'DMSR-8173' by 'DBB Lifetime Management';
  part def 'DBB Lifetime Management SW Def';
  part 'DBB Lifetime Management SW' : 'DBB Lifetime Management SW Def';
  satisfy 'DMSR-2551' by 'DBB Lifetime Management SW';
  satisfy 'DMSR-1436' by 'DBB Lifetime Management SW';
  satisfy 'DMSR-1933' by 'DBB Lifetime Management SW';
  satisfy 'DMSR-3973' by 'DBB Lifetime Management SW';
  satisfy 'DMSR-8173' by 'DBB Lifetime Management SW';
  part def 'Header Service SW Def';
  part 'Header Service SW' : 'Header Service SW Def';
  satisfy 'OCS-DM-COM-ICD-0013' by 'Header Service SW';
  satisfy 'OCS-DM-COM-ICD-0014' by 'Header Service SW';
  satisfy 'OCS-DM-COM-ICD-0015' by 'Header Service SW';
  satisfy 'OCS-DM-COM-ICD-0033' by 'Header Service SW';
  satisfy 'OCS-DM-COM-ICD-0034' by 'Header Service SW';
  satisfy 'OCS-DM-COM-ICD-0036' by 'Header Service SW';
  satisfy 'OCS-DM-COM-ICD-0037' by 'Header Service SW';
  satisfy 'OCS-DM-COM-ICD-0038' by 'Header Service SW';
  satisfy 'OCS-DM-COM-ICD-0039' by 'Header Service SW';
  satisfy 'OCS-DM-COM-ICD-0040' by 'Header Service SW';
  satisfy 'OCS-EFD-HS-0001' by 'Header Service SW';
  satisfy 'OCS-EFD-HS-0002' by 'Header Service SW';
  satisfy 'OCS-EFD-HS-0003' by 'Header Service SW';
  satisfy 'OCS-EFD-HS-0004' by 'Header Service SW';
  satisfy 'OCS-EFD-HS-0005' by 'Header Service SW';
  satisfy 'OCS-EFD-HS-0006' by 'Header Service SW';
  satisfy 'OCS-EFD-HS-0007' by 'Header Service SW';
  satisfy 'OCS-EFD-HS-0008' by 'Header Service SW';
  satisfy 'OCS-EFD-HS-0009' by 'Header Service SW';
  satisfy 'OCS-EFD-HS-0010' by 'Header Service SW';
  satisfy 'OCS-EFD-HS-0011' by 'Header Service SW';
  satisfy 'OCS-EFD-HS-0012' by 'Header Service SW';
  satisfy 'OCS-EFD-HS-0013' by 'Header Service SW';
  satisfy 'OCS-EFD-HS-0014' by 'Header Service SW';
  satisfy 'OCS-EFD-HS-0015' by 'Header Service SW';
  part def '15.2 Component to Requirement Traceability Def';
  part '15.2 Component to Requirement Traceability' : '15.2 Component to Requirement Traceability Def';
  satisfy 'DMSR-8717' by '15.2 Component to Requirement Traceability';
  satisfy 'DMSR-9849' by '15.2 Component to Requirement Traceability';
  satisfy 'DMSR-1155' by '15.2 Component to Requirement Traceability';
  satisfy 'DMSR-8994' by '15.2 Component to Requirement Traceability';
  satisfy 'DMSR-7327' by '15.2 Component to Requirement Traceability';
  satisfy 'DMSR-1623' by '15.2 Component to Requirement Traceability';
  satisfy 'DMSR-8173' by '15.2 Component to Requirement Traceability';
  satisfy 'OCS-DM-COM-ICD-0003' by '15.2 Component to Requirement Traceability';
  satisfy 'OCS-DM-COM-ICD-0004' by '15.2 Component to Requirement Traceability';
  satisfy 'OCS-DM-COM-ICD-0005' by '15.2 Component to Requirement Traceability';
  satisfy 'OCS-DM-COM-ICD-0006' by '15.2 Component to Requirement Traceability';
  satisfy 'OCS-DM-COM-ICD-0008' by '15.2 Component to Requirement Traceability';
  satisfy 'OCS-DM-COM-ICD-0009' by '15.2 Component to Requirement Traceability';
  satisfy 'OCS-DM-COM-ICD-0012' by '15.2 Component to Requirement Traceability';
  satisfy 'OCS-DM-COM-ICD-0013' by '15.2 Component to Requirement Traceability';
  satisfy 'OCS-DM-COM-ICD-0014' by '15.2 Component to Requirement Traceability';
  satisfy 'OCS-DM-COM-ICD-0015' by '15.2 Component to Requirement Traceability';
  satisfy 'OCS-DM-COM-ICD-0025' by '15.2 Component to Requirement Traceability';
  satisfy 'OCS-DM-COM-ICD-0026' by '15.2 Component to Requirement Traceability';
  satisfy 'OCS-DM-COM-ICD-0027' by '15.2 Component to Requirement Traceability';
  satisfy 'OCS-DM-COM-ICD-0028' by '15.2 Component to Requirement Traceability';
  satisfy 'OCS-DM-COM-ICD-0029' by '15.2 Component to Requirement Traceability';
  satisfy 'OCS-DM-COM-ICD-0030' by '15.2 Component to Requirement Traceability';
  satisfy 'OCS-DM-COM-ICD-0032' by '15.2 Component to Requirement Traceability';
  satisfy 'OCS-DM-COM-ICD-0033' by '15.2 Component to Requirement Traceability';
  satisfy 'OCS-DM-COM-ICD-0034' by '15.2 Component to Requirement Traceability';
  satisfy 'OCS-DM-COM-ICD-0036' by '15.2 Component to Requirement Traceability';
  satisfy 'OCS-DM-COM-ICD-0037' by '15.2 Component to Requirement Traceability';
  satisfy 'OCS-DM-COM-ICD-0038' by '15.2 Component to Requirement Traceability';
  satisfy 'OCS-DM-COM-ICD-0039' by '15.2 Component to Requirement Traceability';
  satisfy 'OCS-DM-COM-ICD-0040' by '15.2 Component to Requirement Traceability';
  satisfy 'OCS-DM-COM-ICD-0041' by '15.2 Component to Requirement Traceability';
  satisfy 'OCS-DM-COM-ICD-0042' by '15.2 Component to Requirement Traceability';
  satisfy 'OCS-DM-COM-ICD-0043' by '15.2 Component to Requirement Traceability';
  satisfy 'OCS-DM-COM-ICD-0044' by '15.2 Component to Requirement Traceability';
  satisfy 'OCS-DM-COM-ICD-0045' by '15.2 Component to Requirement Traceability';
  satisfy 'OCS-DM-COM-ICD-0055' by '15.2 Component to Requirement Traceability';
  satisfy 'OCS-EFD-HS-0001' by '15.2 Component to Requirement Traceability';
  satisfy 'OCS-EFD-HS-0002' by '15.2 Component to Requirement Traceability';
  satisfy 'OCS-EFD-HS-0003' by '15.2 Component to Requirement Traceability';
  satisfy 'OCS-EFD-HS-0004' by '15.2 Component to Requirement Traceability';
  satisfy 'OCS-EFD-HS-0005' by '15.2 Component to Requirement Traceability';
  satisfy 'OCS-EFD-HS-0006' by '15.2 Component to Requirement Traceability';
  satisfy 'OCS-EFD-HS-0007' by '15.2 Component to Requirement Traceability';
  satisfy 'OCS-EFD-HS-0008' by '15.2 Component to Requirement Traceability';
  satisfy 'OCS-EFD-HS-0009' by '15.2 Component to Requirement Traceability';
  satisfy 'OCS-EFD-HS-0010' by '15.2 Component to Requirement Traceability';
  satisfy 'OCS-EFD-HS-0011' by '15.2 Component to Requirement Traceability';
  satisfy 'OCS-EFD-HS-0012' by '15.2 Component to Requirement Traceability';
  satisfy 'OCS-EFD-HS-0013' by '15.2 Component to Requirement Traceability';
  satisfy 'OCS-EFD-HS-0014' by '15.2 Component to Requirement Traceability';
  satisfy 'OCS-EFD-HS-0015' by '15.2 Component to Requirement Traceability';
  satisfy 'OCS-DM-COM-ICD-0046' by '15.2 Component to Requirement Traceability';
  satisfy 'OCS-DM-COM-ICD-0056' by '15.2 Component to Requirement Traceability';
  satisfy 'DMSR-4591' by '15.2 Component to Requirement Traceability';
  satisfy 'OCS-DM-COM-ICD-0017' by '15.2 Component to Requirement Traceability';
  satisfy 'OCS-DM-COM-ICD-0018' by '15.2 Component to Requirement Traceability';
  satisfy 'OCS-DM-COM-ICD-0019' by '15.2 Component to Requirement Traceability';
  satisfy 'OCS-DM-COM-ICD-0020' by '15.2 Component to Requirement Traceability';
  satisfy 'OCS-DM-COM-ICD-0021' by '15.2 Component to Requirement Traceability';
  satisfy 'OCS-DM-COM-ICD-0022' by '15.2 Component to Requirement Traceability';
  satisfy 'OCS-DM-COM-ICD-0047' by '15.2 Component to Requirement Traceability';
  satisfy 'OCS-DM-COM-ICD-0048' by '15.2 Component to Requirement Traceability';
  satisfy 'OCS-DM-COM-ICD-0049' by '15.2 Component to Requirement Traceability';
  satisfy 'OCS-DM-COM-ICD-0050' by '15.2 Component to Requirement Traceability';
  satisfy 'OCS-DM-COM-ICD-0051' by '15.2 Component to Requirement Traceability';
  satisfy 'OCS-DM-COM-ICD-0052' by '15.2 Component to Requirement Traceability';
  satisfy 'OCS-DM-COM-ICD-0053' by '15.2 Component to Requirement Traceability';
  satisfy 'OCS-DM-COM-ICD-0054' by '15.2 Component to Requirement Traceability';
  satisfy 'DMSR-8525' by '15.2 Component to Requirement Traceability';
  satisfy 'DMSR-2005' by '15.2 Component to Requirement Traceability';
  satisfy 'DMSR-3617' by '15.2 Component to Requirement Traceability';
  satisfy 'DMSR-8494' by '15.2 Component to Requirement Traceability';
  satisfy 'DMSR-3337' by '15.2 Component to Requirement Traceability';
  satisfy 'DMSR-3443' by '15.2 Component to Requirement Traceability';
  satisfy 'DMSR-4522' by '15.2 Component to Requirement Traceability';
  satisfy 'DMSR-1601' by '15.2 Component to Requirement Traceability';
  satisfy 'DMSR-3731' by '15.2 Component to Requirement Traceability';
  satisfy 'DMSR-9599' by '15.2 Component to Requirement Traceability';
  satisfy 'DMSR-7847' by '15.2 Component to Requirement Traceability';
  satisfy 'DMSR-1963' by '15.2 Component to Requirement Traceability';
  satisfy 'DMSR-3004' by '15.2 Component to Requirement Traceability';
  satisfy 'DMSR-3997' by '15.2 Component to Requirement Traceability';
  satisfy 'DMSR-5909' by '15.2 Component to Requirement Traceability';
  satisfy 'DMSR-6640' by '15.2 Component to Requirement Traceability';
  satisfy 'DMSR-6663' by '15.2 Component to Requirement Traceability';
  satisfy 'DMSR-8700' by '15.2 Component to Requirement Traceability';
  satisfy 'DMSR-8104' by '15.2 Component to Requirement Traceability';
  satisfy 'DMSR-3757' by '15.2 Component to Requirement Traceability';
  satisfy 'DMSR-1570' by '15.2 Component to Requirement Traceability';
  satisfy 'DMSR-8254' by '15.2 Component to Requirement Traceability';
  satisfy 'DMSR-3565' by '15.2 Component to Requirement Traceability';
  satisfy 'DMSR-9563' by '15.2 Component to Requirement Traceability';
  satisfy 'DMSR-3002' by '15.2 Component to Requirement Traceability';
  satisfy 'DMSR-3967' by '15.2 Component to Requirement Traceability';
  satisfy 'DMSR-7545' by '15.2 Component to Requirement Traceability';
  satisfy 'DMSR-3705' by '15.2 Component to Requirement Traceability';
  satisfy 'DMSR-9395' by '15.2 Component to Requirement Traceability';
  satisfy 'DMSR-1602' by '15.2 Component to Requirement Traceability';
  satisfy 'DMSR-9631' by '15.2 Component to Requirement Traceability';
  satisfy 'DMSR-8663' by '15.2 Component to Requirement Traceability';
  satisfy 'DMSR-2203' by '15.2 Component to Requirement Traceability';
  satisfy 'DMSR-5575' by '15.2 Component to Requirement Traceability';
  satisfy 'DMSR-3973' by '15.2 Component to Requirement Traceability';
  satisfy 'DMSR-1851' by '15.2 Component to Requirement Traceability';
  satisfy 'DMSR-3852' by '15.2 Component to Requirement Traceability';
  satisfy 'DMSR-7695' by '15.2 Component to Requirement Traceability';
  satisfy 'DMSR-2551' by '15.2 Component to Requirement Traceability';
  satisfy 'DMSR-1436' by '15.2 Component to Requirement Traceability';
  satisfy 'DMSR-1933' by '15.2 Component to Requirement Traceability';
  satisfy 'DMSR-6131' by '15.2 Component to Requirement Traceability';
  satisfy 'DMSR-2053' by '15.2 Component to Requirement Traceability';
  satisfy 'DMSR-3710' by '15.2 Component to Requirement Traceability';
  satisfy 'DMSR-1961' by '15.2 Component to Requirement Traceability';
  satisfy 'DMSR-3608' by '15.2 Component to Requirement Traceability';
  satisfy 'DMSR-6487' by '15.2 Component to Requirement Traceability';
  satisfy 'DMSR-1919a' by '15.2 Component to Requirement Traceability';
  satisfy 'DMSR-6519a' by '15.2 Component to Requirement Traceability';
  satisfy 'DMSR-3569b' by '15.2 Component to Requirement Traceability';
  satisfy 'DMSR-6377' by '15.2 Component to Requirement Traceability';
  satisfy 'DMSR-3446' by '15.2 Component to Requirement Traceability';
  satisfy 'DMSR-9570' by '15.2 Component to Requirement Traceability';
  satisfy 'DMSR-1538' by '15.2 Component to Requirement Traceability';
  satisfy 'DMSR-6585' by '15.2 Component to Requirement Traceability';
  satisfy 'DMSR-8325' by '15.2 Component to Requirement Traceability';
  satisfy 'DMSR-6475' by '15.2 Component to Requirement Traceability';
  satisfy 'DMSR-3919' by '15.2 Component to Requirement Traceability';
  satisfy 'DMSR-9625' by '15.2 Component to Requirement Traceability';
  satisfy 'DMSR-5731' by '15.2 Component to Requirement Traceability';
  satisfy 'DMSR-5135' by '15.2 Component to Requirement Traceability';
  satisfy 'DMSR-5792' by '15.2 Component to Requirement Traceability';
  satisfy 'DMSR-5457' by '15.2 Component to Requirement Traceability';
  satisfy 'DMSR-1083' by '15.2 Component to Requirement Traceability';
  satisfy 'DMSR-8804' by '15.2 Component to Requirement Traceability';
  satisfy 'DMSR-9748' by '15.2 Component to Requirement Traceability';
  satisfy 'DMSR-4497' by '15.2 Component to Requirement Traceability';
  satisfy 'DMSR-3406' by '15.2 Component to Requirement Traceability';
  satisfy 'DMSR-1376' by '15.2 Component to Requirement Traceability';
  satisfy 'DMSR-5600' by '15.2 Component to Requirement Traceability';
  satisfy 'DMSR-3770' by '15.2 Component to Requirement Traceability';
  satisfy 'DMSR-6987' by '15.2 Component to Requirement Traceability';
  satisfy 'DMSR-8958b' by '15.2 Component to Requirement Traceability';
  satisfy 'DMSR-8595' by '15.2 Component to Requirement Traceability';
  satisfy 'DMSR-7328' by '15.2 Component to Requirement Traceability';
  satisfy 'DMSR-3743' by '15.2 Component to Requirement Traceability';
  satisfy 'DMSR-1614' by '15.2 Component to Requirement Traceability';
  satisfy 'DMSR-5040' by '15.2 Component to Requirement Traceability';
  satisfy 'DMSR-4348' by '15.2 Component to Requirement Traceability';
  satisfy 'EP-DM-CON-ICD-0034' by '15.2 Component to Requirement Traceability';
  satisfy 'EP-DM-CON-ICD-0036' by '15.2 Component to Requirement Traceability';
  satisfy 'DMSR-5500' by '15.2 Component to Requirement Traceability';
  satisfy 'DMSR-6792' by '15.2 Component to Requirement Traceability';
  satisfy 'DMSR-1431' by '15.2 Component to Requirement Traceability';
  satisfy 'DMSR-9056' by '15.2 Component to Requirement Traceability';
  satisfy 'DMSR-9126' by '15.2 Component to Requirement Traceability';
  satisfy 'DMSR-1111' by '15.2 Component to Requirement Traceability';
  satisfy 'DMSR-4054' by '15.2 Component to Requirement Traceability';
  satisfy 'DMSR-2784' by '15.2 Component to Requirement Traceability';
  satisfy 'DMSR-6406' by '15.2 Component to Requirement Traceability';
  satisfy 'DMSR-8704' by '15.2 Component to Requirement Traceability';
  satisfy 'DMSR-8924' by '15.2 Component to Requirement Traceability';
  satisfy 'DMSR-4012' by '15.2 Component to Requirement Traceability';
  satisfy 'DMSR-1060' by '15.2 Component to Requirement Traceability';
  satisfy 'DMSR-8973' by '15.2 Component to Requirement Traceability';
  satisfy 'DMSR-5264' by '15.2 Component to Requirement Traceability';
  satisfy 'DMSR-7938' by '15.2 Component to Requirement Traceability';
  satisfy 'DMSR-8661' by '15.2 Component to Requirement Traceability';
  satisfy 'DMSR-9022' by '15.2 Component to Requirement Traceability';
  satisfy 'DMSR-9439' by '15.2 Component to Requirement Traceability';
  satisfy 'DMSR-3539' by '15.2 Component to Requirement Traceability';
  satisfy 'DMSR-8956' by '15.2 Component to Requirement Traceability';
  satisfy 'DMSR-5586' by '15.2 Component to Requirement Traceability';
  satisfy 'DMSR-9307' by '15.2 Component to Requirement Traceability';
  satisfy 'DMSR-9497' by '15.2 Component to Requirement Traceability';
  satisfy 'DMSR-1591' by '15.2 Component to Requirement Traceability';
  satisfy 'DMSR-3753' by '15.2 Component to Requirement Traceability';
  satisfy 'DMSR-9580' by '15.2 Component to Requirement Traceability';
  satisfy 'DMSR-8635' by '15.2 Component to Requirement Traceability';
  satisfy 'DMSR-9850' by '15.2 Component to Requirement Traceability';
  satisfy 'DMSR-5454' by '15.2 Component to Requirement Traceability';
  satisfy 'DMSR-7791' by '15.2 Component to Requirement Traceability';
  satisfy 'DMSR-6625' by '15.2 Component to Requirement Traceability';
  satisfy 'DMSR-5826' by '15.2 Component to Requirement Traceability';
  satisfy 'DMSR-7450' by '15.2 Component to Requirement Traceability';
  satisfy 'DMSR-6570' by '15.2 Component to Requirement Traceability';
  satisfy 'DMSR-6300' by '15.2 Component to Requirement Traceability';
  satisfy 'DMSR-3410' by '15.2 Component to Requirement Traceability';
  satisfy 'DMSR-4721' by '15.2 Component to Requirement Traceability';
  satisfy 'DMSR-2240' by '15.2 Component to Requirement Traceability';
  satisfy 'DMSR-4765' by '15.2 Component to Requirement Traceability';
  satisfy 'EP-DM-CON-ICD-0035' by '15.2 Component to Requirement Traceability';
  satisfy 'DMSR-8893' by '15.2 Component to Requirement Traceability';
  satisfy 'DMSR-9422' by '15.2 Component to Requirement Traceability';
  satisfy 'DMSR-3721' by '15.2 Component to Requirement Traceability';
  satisfy 'DMSR-2127' by '15.2 Component to Requirement Traceability';
  satisfy 'DMSR-6155' by '15.2 Component to Requirement Traceability';
  satisfy 'DMSR-1765' by '15.2 Component to Requirement Traceability';
  satisfy 'DMSR-8537' by '15.2 Component to Requirement Traceability';
  satisfy 'DMSR-1632' by '15.2 Component to Requirement Traceability';
  satisfy 'DMSR-6206' by '15.2 Component to Requirement Traceability';
  satisfy 'DMSR-7456' by '15.2 Component to Requirement Traceability';
  satisfy 'DMSR-6515' by '15.2 Component to Requirement Traceability';
  satisfy 'DMSR-3612' by '15.2 Component to Requirement Traceability';
  satisfy 'DMSR-9308' by '15.2 Component to Requirement Traceability';
  satisfy 'EP-DM-CON-ICD-0002' by '15.2 Component to Requirement Traceability';
  satisfy 'DMSR-9198' by '15.2 Component to Requirement Traceability';
  satisfy 'OCS-DM-COM-ICD-0007' by '15.2 Component to Requirement Traceability';
  part def 'Planned Observation Publication Def';
  part 'Planned Observation Publication' : 'Planned Observation Publication Def';
  satisfy 'DMSR-9198' by 'Planned Observation Publication';
  part def 'Prompt Quality Control Def';
  part 'Prompt Quality Control' : 'Prompt Quality Control Def';
  satisfy 'DMSR-8983' by 'Prompt Quality Control';
  satisfy 'DMSR-9060' by 'Prompt Quality Control';
  satisfy 'DMSR-1066' by 'Prompt Quality Control';
  satisfy 'DMSR-2875' by 'Prompt Quality Control';
  satisfy 'DMSR-3448' by 'Prompt Quality Control';
  satisfy 'DMSR-9791' by 'Prompt Quality Control';
  satisfy 'DMSR-8994' by 'Prompt Quality Control';
  satisfy 'DMSR-1623' by 'Prompt Quality Control';
  part def 'Planned Observation Publication SW Def';
  part 'Planned Observation Publication SW' : 'Planned Observation Publication SW Def';
  satisfy 'DMSR-9198' by 'Planned Observation Publication SW';
  part def 'Quality Control SW Def';
  part 'Quality Control SW' : 'Quality Control SW Def';
  satisfy 'DMSR-8983' by 'Quality Control SW';
  satisfy 'DMSR-9060' by 'Quality Control SW';
  satisfy 'DMSR-1066' by 'Quality Control SW';
  satisfy 'DMSR-2875' by 'Quality Control SW';
  satisfy 'DMSR-3448' by 'Quality Control SW';
  satisfy 'DMSR-9791' by 'Quality Control SW';
  satisfy 'DMSR-8994' by 'Quality Control SW';
  satisfy 'DMSR-1623' by 'Quality Control SW';
  part def 'Special Programs Productions Def';
  part 'Special Programs Productions' : 'Special Programs Productions Def';
  satisfy 'DMSR-5586' by 'Special Programs Productions';
  satisfy 'DMSR-7695' by 'Special Programs Productions';
  part def 'Template Generation Def';
  part 'Template Generation' : 'Template Generation Def';
  satisfy 'DMSR-9439' by 'Template Generation';
  satisfy 'DMSR-8956' by 'Template Generation';
}
